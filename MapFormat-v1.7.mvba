Attribute VB_Name = "Arrays"
Public Sub QuickActionSort(vArray() As Map, inLow As Long, inHi As Long)
  Dim pivot   As Map
  Dim tmpSwap As Map
  Dim tmpLow  As Long
  Dim tmpHi   As Long

  tmpLow = inLow
  tmpHi = inHi
  
  Set pivot = vArray((inLow + inHi) \ 2)

  While (tmpLow <= tmpHi)
     While (vArray(tmpLow).getMapValue() < pivot.getMapValue() And tmpLow < inHi)
        tmpLow = tmpLow + 1
     Wend

     While (pivot.getMapValue() < vArray(tmpHi).getMapValue() And tmpHi > inLow)
        tmpHi = tmpHi - 1
     Wend

     If (tmpLow <= tmpHi) Then
        Set tmpSwap = vArray(tmpLow)
        Set vArray(tmpLow) = vArray(tmpHi)
        Set vArray(tmpHi) = tmpSwap
        tmpLow = tmpLow + 1
        tmpHi = tmpHi - 1
     End If
  Wend

  If (inLow < tmpHi) Then QuickActionSort vArray, inLow, tmpHi
  If (tmpLow < inHi) Then QuickActionSort vArray, tmpLow, inHi
End Sub

Public Sub QuickActionRoadSort(vArray() As Road, inLow As Long, inHi As Long)
  Dim pivot   As Road
  Dim tmpSwap As Road
  Dim tmpLow  As Long
  Dim tmpHi   As Long

  tmpLow = inLow
  tmpHi = inHi
  
  Set pivot = vArray((inLow + inHi) \ 2)

  While (tmpLow <= tmpHi)
     While (vArray(tmpLow).compareRoad(pivot) < 0 And tmpLow < inHi)
        tmpLow = tmpLow + 1
     Wend

     While (pivot.compareRoad(vArray(tmpHi)) < 0 And tmpHi > inLow)
        tmpHi = tmpHi - 1
     Wend

     If (tmpLow <= tmpHi) Then
        Set tmpSwap = vArray(tmpLow)
        Set vArray(tmpLow) = vArray(tmpHi)
        Set vArray(tmpHi) = tmpSwap
        tmpLow = tmpLow + 1
        tmpHi = tmpHi - 1
     End If
  Wend

  If (inLow < tmpHi) Then QuickActionRoadSort vArray, inLow, tmpHi
  If (tmpLow < inHi) Then QuickActionRoadSort vArray, tmpLow, inHi
End Sub

Attribute VB_Name = "CountingModule"
' Sort non SR,NC,or US roads on top from other names

Function SumCenterlines()
    If Not ActiveDesignFile.Fence.IsDefined Then
        MsgBox "A fence needs to be defined."
        Exit Function
    End If
    Dim ee As ElementEnumerator
    Set ee = ActiveDesignFile.Fence.GetContents(True)
    Dim sum As Double
    sum = 0
    Dim oElem As Element
    While ee.MoveNext
        If ee.Current.IsChainableElement Then
            If ee.Current.Level.name = "Exist Horizontal Alignment" Then
                sum = sum + ee.Current.AsChainableElement.Length
            End If
        End If
    Wend
    MsgBox "Total Centerline Length: " & CLng(sum) & " feet.", vbInformation, "Centerline Sum"
End Function

Function RoadConversion()
    If Not ActiveDesignFile.Fence.IsDefined Then
        MsgBox "A fence needs to be defined."
        Exit Function
    End If
    
    Dim oFence As Fence
    Dim oElem As Element
    Dim myView As View
    
    
     With ActiveSettings
        .FenceClip = False
        .FenceOverlap = True
    End With

    Set oFence = ActiveDesignFile.Fence

    'Debug.Print "View: " & oFence.
    'See CopyFenceContents() example to possible implement saving the active settings (probably should do outside this method)
    Dim ee As ElementEnumerator
    Set ee = oFence.GetContents(True)
    
    Dim roadElements As New Collection
    Dim newRoad As Road
    Dim currRoad As Road
    Dim unique As Boolean
    Dim handHoles As Integer
    Dim shownError As Boolean
    shownError = False
    handHoles = 0
    While ee.MoveNext
        Set oElem = ee.Current
        If Not oElem.Level Is Nothing And oElem.IsTextNodeElement Then
        Debug.Print oElem.AsTextNodeElement.origin.X & " " & oElem.AsTextNodeElement.origin.Y
            If oElem.Level.name = "CATV Line UBO Text" Then
                'Extract data from text
                Set newRoad = ExtractLineType(oElem.AsTextNodeElement)
                If newRoad.RoadName = "SR-1234" And Not shownError Then
                    MsgBox "Found default road number: SR-1234" & vbNewLine & "Double check you actually have this road in the project."
                    shownError = True
                End If
                ' See if the road can be added to an existing one
                unique = True
                For i = 1 To roadElements.Count
                    Set currRoad = roadElements.Item(i)
                    If currRoad.BoreType = newRoad.BoreType And currRoad.Along = newRoad.Along And currRoad.RoadName = newRoad.RoadName Then
                        unique = False
                        currRoad.Length = currRoad.Length + newRoad.Length
                        Exit For
                    End If
                Next i
                If unique Then roadElements.Add newRoad
            End If
        ElseIf oElem.IsCellElement Then
            If oElem.AsCellElement.name = "EXIST UTILITIES TELEPHONE HAND HOLE" Then
                handHoles = handHoles + 1
            End If
        End If
    Wend
    
    If roadElements.Count = 0 Then
        MsgBox "No elements found"
        Exit Function
    End If
    'Sort new road
    Dim allRoads() As Road
    ReDim allRoads(0 To roadElements.Count - 1)
    For i = 1 To roadElements.Count
        Set allRoads(i - 1) = roadElements.Item(i)
    Next i
    
    Arrays.QuickActionRoadSort allRoads, 0, roadElements.Count - 1
    
    Dim strPath As String
    strPath = ActiveDesignFile.Path & "\Converted_Roads.txt"
    Dim fso As Object
    Set fso = CreateObject("Scripting.FileSystemObject")
    Dim oFile As Object
    On Error GoTo 0
    Set oFile = fso.CreateTextFile(strPath, True)
    
    
    Dim uniqueRoads As New Collection
    Dim numRoads As Integer
    numRoads = 0
    Dim totalPlow As Long
    totalPlow = 0
    Dim boreAlong As Long
    Dim boreAcross As Long
    boreAlong = 0
    boreAcross = 0
    For i = 0 To roadElements.Count - 1
        Set currRoad = allRoads(i)
        unique = True
        For j = 1 To uniqueRoads.Count
            If uniqueRoads.Item(j) = currRoad.RoadName Then
                unique = False
                Exit For
            End If
        Next j
        If unique Then
            uniqueRoads.Add currRoad.RoadName
            numRoads = numRoads + 1
            If uniqueRoads.Count > 1 Then
                Debug.Print ""
                oFile.WriteLine ""
            End If
        End If
        Debug.Print currRoad.ToString()
        oFile.WriteLine currRoad.ToString()
        If currRoad.IsConventionalBore Then
            If currRoad.Along Then
                boreAlong = boreAlong + currRoad.Length
            Else
                boreAcross = boreAcross + currRoad.Length
            End If
        Else
            totalPlow = totalPlow + currRoad.Length
        End If
    Next i
    
    oFile.WriteLine ""
    Debug.Print ""
    
    Dim plowText As String
    Dim boreAlongText As String
    Dim boreAcrossText As String
    Dim boreTotal As String
    Dim total As String
    Dim totalRoads As String
    Dim roadList As String
    Dim handHoleText As String
    
    plowText = "Plow total: " & totalPlow & " feet."
    boreAlongText = "Directional Bore Along Total: " & boreAlong & " feet."
    boreAcrossText = "Directional Bore Across Total: " & boreAcross & " feet."
    boreTotal = "Bore Total: " & boreAlong + boreAcross & " feet."
    total = "Total Plow + Bore: " & boreAlong + boreAcross + totalPlow & " feet."
    totalRoads = numRoads & " different roads in this segment."
    handHoleText = "A total of " & handHoles & " new ANSI/SCTE Tier 22 handholes placed in right of way."
    
    Dim roadText As String
    roadText = ""
    For i = 1 To uniqueRoads.Count
        If roadText <> "" And uniqueRoads.Count > 2 Then roadText = roadText & ","
        If roadText <> "" Then roadText = roadText & " "
        If i = uniqueRoads.Count And i <> 1 Then roadText = roadText & "and "
        roadText = roadText & uniqueRoads.Item(i)
    Next i
    
    oFile.WriteLine boreTotal
    oFile.WriteLine plowText
    oFile.WriteLine boreAlongText
    oFile.WriteLine boreAcrossText
    oFile.WriteLine total
    oFile.WriteLine ""
    oFile.WriteLine totalRoads
    oFile.WriteLine roadText
    oFile.WriteLine ""
    oFile.WriteLine handHoleText
    
    Debug.Print plowText
    Debug.Print boreTotal
    Debug.Print boreAlongText
    Debug.Print boreAcrossText
    Debug.Print total
    Debug.Print ""
    Debug.Print totalRoads
    Debug.Print roadText
    Debug.Print ""
    Debug.Print handHoleText
    
    oFile.Close
    Set fso = Nothing
    Set oFile = Nothing
    
    MsgBox total & vbNewLine & "See file for more details: " & Chr(34) & strPath & Chr(34), vbInformation, "Calculate"
End Function

Function ExtractLineType(lineDim As TextNodeElement) As Road
    Dim currRoad As New Road
    currRoad.BoreType = lineDim.TextLine(1)
    
    Dim line2() As String
    line2 = Split(lineDim.TextLine(2), " ")
    currRoad.Length = CInt(line2(0))
    If line2(2) = "ALONG" Then
        currRoad.Along = True
    Else
        currRoad.Along = False
    End If
    
    Dim name As String
    name = ""
    For i = 3 To UBound(line2)
        If i <> 3 Then name = name & " "
        name = name & line2(i)
    Next i
    currRoad.RoadName = name
    Set ExtractLineType = currRoad
End Function

Attribute VB_Name = "Map"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private map_contents As Collection
Private road_names As Collection
Private corner As Point3d
Private main_boundary As ComplexShapeElement
Private original_boundary As ComplexShapeElement

Private map_num As String

Property Get MapNumber() As String
    MapNumber = map_num
End Property

Property Let MapNumber(mapNum As String)
    map_num = mapNum
End Property

'Returns the road names in the map
Public Function getRoadNames() As Collection
    Set getRoadNames = road_names
End Function

Public Sub SetRoadNames(roadNames As Collection)
    Set road_names = roadNames
End Sub

Public Sub SetContents(MapContents As Collection)
    Set map_contents = MapContents
End Sub

Property Let MainBoundary(boundary As ComplexShapeElement)
    Dim cContext As New CopyContext
    cContext.AddElementToModel = False
    Set original_boundary = ActiveModelReference.CopyElement(boundary, cContext)
    Set main_boundary = boundary
End Property

Property Get MainBoundary() As ComplexShapeElement
    Set MainBoundary = main_boundary
End Property

Function GetOriginalBoundary() As ComplexShapeElement
    Set GetOriginalBoundary = original_boundary
End Function

Public Function getMapValue() As Double
Dim letterAddition As Double
Dim ascii As Integer
ascii = Asc(Right(map_num, 1))
If ascii > 57 Then
    'Letter
    letterAddition = CInt(Left(map_num, Len(map_num) - 1)) + (ascii / 255)
Else
    letterAddition = CInt(map_num)
End If
getMapValue = letterAddition

End Function

Property Let CornerPoint(corner_point As Point3d)
    corner = corner_point
End Property

Property Get CornerPoint() As Point3d
    CornerPoint = corner
End Property

' This is not used anymore, instead the map is placed in MapFormatModule.FormatMap
Public Sub PlaceMap(tlCorner As Point3d)
    Dim moveDistance As Point3d
    moveDistance = Point3dSubtract(tlCorner, corner)
    
    Dim ele As Element
    Dim oDimStyle As DimensionStyle
    For i = 1 To map_contents.Count
        Set ele = map_contents.Item(i)
        ele.Move moveDistance
        If MapFormatForm.ChangeToWhite Then
            If ele.IsGraphical Then
                If ele.IsCellElement Then
                    'Check cell name for color change
                    If ele.AsCellElement.name <> "EXIST UTILITIES TELEPHONE HAND HOLE" And ele.AsCellElement.name <> "EXIST UTILITIES TV PEDESTAL" Then
                        'Change to white
                        ele.AsCellElement.Color = 0
                    End If
                ElseIf Not ele.Level Is Nothing Then
                    'Check levels for color change
                    If ele.Level.name <> "Level 30" And ele.Level.name <> "CATV Line UBO Text" And ele.Level.name <> "Level 12" And Not IsBorePit(ele) Then
                        'Change to white
                        If ele.IsDimensionElement Then
                            'Extract style to change all elements to white
                            Set oDimStyle = ele.AsDimensionElement.DimensionStyle
                            oDimStyle.OverallColor = 0
                            oDimStyle.OverrideExtensionLineColor = False
                            ele.AsDimensionElement.DimensionStyle = oDimStyle
                        End If
                        ele.Color = 0
                    End If
                End If
            End If
        End If
        If ele.IsComplexShapeElement Then
            If ele.Level.name <> "Level 63" Then
                ActiveModelReference.AddElement ele
                ele.Rewrite
                ele.Redraw
            End If
        Else
            ActiveModelReference.AddElement ele
            ele.Rewrite
            ele.Redraw
        End If
    Next i
End Sub

Private Sub Class_Initialize()
    map_num = "0"
End Sub

Attribute VB_Name = "MapFormatForm"
Attribute VB_Base = "0{DA64F8CD-BA5E-44B0-8D3E-C6282C724F36}{6B7174DD-CF0C-4D93-982F-B9D0F1537E7B}"
Attribute VB_GlobalNameSpace = False
Attribute VB_Creatable = False
Attribute VB_PredeclaredId = True
Attribute VB_Exposed = False
Attribute VB_TemplateDerived = False
Attribute VB_Customizable = False


Private Sub CommandButton1_Click()
    MapFormatModule.SetRange 1
End Sub

Private Sub CommandButton2_Click()
    MapFormatModule.SetRange 2
End Sub

Private Sub CommandButton3_Click()
    MapFormatModule.SetRange 3
End Sub


Private Sub CommandButton4_Click()
    CountingModule.RoadConversion
End Sub

Private Sub CommandButton5_Click()
    CountingModule.SumCenterlines
End Sub

Private Sub RunMapFormat_Click()
    MapFormatModule.FormatMaps
End Sub

Private Sub TextBox1_Change()

End Sub

Attribute VB_Name = "MapFormatModule"
Sub launchForm()
    MapFormatForm.Show vbModless
End Sub

'Matchline center needs to be based on text
'Match lines don't work correctly if they are slighyly outside the blue boxes
'RR Signal doesnt turn to white

Function FormatMaps()
    Debug.Print "Map Format Start"
    MS_DISABLEWINDOWGHOSTING = 1
    'Get starting element from selection
    If Not ActiveModelReference.AnyElementsSelected Or Not ActiveDesignFile.Fence.IsDefined Then
        MsgBox "The macro requires a selection set and a fence"
        Exit Function
    End If
    ProgressBar.CreateForm
    ProgressBar.WriteMessage "0% (Collecting Map Numbers)"
    Dim titleSheet As New Collection
    Dim ee As ElementEnumerator
    Set ee = ActiveModelReference.GetSelectedElements 'Selected elements
    ee.Reset
    While ee.MoveNext
        'Make sure the element is graphical
        If ee.Current.IsGraphical Then
            titleSheet.Add ee.Current
        End If
    Wend
    
    Dim mapBoundaries As Collection
    Set mapBoundaries = getSelectedMapBoundaries()
    ProgressBar.UpdateProgress 1, mapBoundaries.Count, 0
    
    Dim allMapNumbers As Collection
    If MapFormatForm.OffsetByNumber Then
        Set allMapNumbers = getAllMapNumbers()
    End If
    
    breakBoundaryIntersections mapBoundaries
    
    Dim originalExtents As Point3d
    Dim originalView As View
    Dim originalCenter As Point3d
    Set originalView = CommandState.LastView
    originalExtents = originalView.Extents
    originalCenter = originalView.center
    
    Dim maps() As Map
    ReDim maps(mapBoundaries.Count)
    
    'Format maps from map boundaries
    Dim mapObj As Map
    For i = 1 To mapBoundaries.Count
        Set mapObj = initializeMap(mapBoundaries.Item(i))
        If mapObj Is Nothing Then
            Exit Function
        End If
        If i = 1 And MapFormatForm.CopyRaster Then
            If GetRaster(mapObj.CornerPoint) Is Nothing Then
                MsgBox "Could not get raster."
                Unload ProgressForm
                Exit Function
            End If
        End If
        Set maps(i - 1) = mapObj
    Next i
    
    originalView.Extents = originalExtents
    originalView.center = originalCenter
    originalView.Redraw
    
    'Remove titlesheet elements
    For i = 1 To titleSheet.Count
        ActiveModelReference.RemoveElement titleSheet.Item(i)
    Next i
    
    'Sort the maps by map number
    Arrays.QuickActionSort maps, 0, mapBoundaries.Count - 1
    
    'Display maps
    Dim corner As Point3d
    corner = getTitleCorner(titleSheet)
    'Debug.Print corner.X & " " & corner.Y
    Dim moveDistance As Point3d
    Const mapSpacing As Double = -1200
    Dim offsetScale As Integer
    Dim progressPercent As Double
    
    For i = 0 To mapBoundaries.Count - 1
        offsetScale = i
        If MapFormatForm.OffsetByNumber Then
            For j = 1 To allMapNumbers.Count
                If maps(i).MapNumber = allMapNumbers.Item(j) Then
                    offsetScale = j - 1
                    Exit For
                End If
            Next j
        End If
        moveDistance = Point3dScale(Point3dFromXY(0, mapSpacing), offsetScale)
        Set mapObj = FormatMap(maps(i), corner, moveDistance)
        
        PlaceTitleSheet titleSheet, mapObj.MapNumber, mapObj.getRoadNames, moveDistance
        
        progressPercent = CDbl(i + 1) / CDbl(mapBoundaries.Count)
        ProgressBar.UpdateProgress i + 1, mapBoundaries.Count, progressPercent
    Next i
    ActiveDesignFile.Fence.Undefine
    Unload ProgressForm
    RasterModule.EndImageExport
End Function

Function initializeMap(boundary As ComplexShapeElement) As Map
    Dim Map As New Map
    Map.MainBoundary = boundary
    Dim mapNumString As String
    mapNumString = getMapNum(boundary)
    If mapNumString = "-1" Then
        Set initializeMap = Nothing
        Exit Function
    End If
    Map.MapNumber = mapNumString
    Set initializeMap = Map
End Function

Function getMapNum(boundary As ComplexShapeElement) As String
    Dim oFence As Fence
        Dim oElem As Element
        Dim myView As View
        
        With ActiveSettings
            .FenceClip = False
            .FenceOverlap = True
        End With
    
        Set oFence = ActiveDesignFile.Fence
        oFence.Undefine
    
        Set myView = CommandState.LastView
    
        oFence.DefineFromElement myView, boundary
        oFence.Draw
        
        Dim fenceEE As ElementEnumerator
        Set fenceEE = oFence.GetContents(True)
        Dim savedNum As String
        savedNum = "0"
        'Iterate through contents
        Dim mapEle As Element
        While fenceEE.MoveNext
            Set mapEle = fenceEE.Current
            If mapEle.IsTextElement And Not mapEle.Level Is Nothing Then
                If mapEle.Level.name = "Level 62" Then
                    If savedNum <> "0" Then
                        Debug.Print "Found multiple map numbers in the same frame: Map-" & savedNum
                        Dim otherMap As String
                        otherMap = Right(mapEle.AsTextElement.text, Len(mapEle.AsTextElement.text) - 4)
                        ZoomBoundary boundary, myView
                        Unload ProgressForm
                        ActiveModelReference.UnselectAllElements
                        MsgBox "Found multiple map numbers in the same frame: Map-" & savedNum & " and Map-" & otherMap & "." & vbNewLine & "Please fix and run the program again.", vbCritical, "Formatting Error"
                        getMapNum = "-1"
                        Exit Function
                    End If
                    savedNum = Right(mapEle.AsTextElement.text, Len(mapEle.AsTextElement.text) - 4)
                End If
            ElseIf mapEle.IsLineElement And Not mapEle.Level Is Nothing Then
                If mapEle.Level.name = "Matchline" Then
                    If UBound(mapEle.AsLineElement.GetIntersectionPoints(boundary, Matrix3dIdentity)) <> -1 Then
                        Debug.Print "Match line intersecting!"
                        ZoomBoundary boundary, myView
                        Dim Answer As Integer
                        Answer = MsgBox("Found match line that is intersecting the map boundary!" & vbNewLine & "If this match line doesn't connect to this map, hit OK, otherwise, Cancel.", vbOKCancel, "Formatting Error")
                        If Answer = vbCancel Then
                            Unload ProgressForm
                            ActiveModelReference.UnselectAllElements
                            getMapNum = "-1"
                            Exit Function
                        End If
                    End If
                End If
            End If
            
        Wend
        getMapNum = savedNum
End Function

Function ZoomBoundary(boundary As ComplexShapeElement, myView As View)
    Dim boundaryThickness As Point3d
    boundaryThickness = myView.Extents
    Dim ratioX As Double
    ratioX = 5100 / boundaryThickness.X
    Dim ratioY As Double
    ratioY = 3300 / boundaryThickness.Y
    If ratioX > ratioY Then
        myView.ZoomAboutPoint boundary.Centroid, ratioX
    Else
        myView.ZoomAboutPoint boundary.Centroid, ratioY
    End If
    myView.Redraw
End Function

Function breakBoundaryIntersections(boundaries As Collection)
    Dim ee As ElementEnumerator
    Dim oScanCriteria As ElementScanCriteria
    Set oScanCriteria = New ElementScanCriteria
    oScanCriteria.ExcludeAllTypes
    oScanCriteria.IncludeType msdElementTypeLineString
    oScanCriteria.IncludeType msdElementTypeShape
    Set ee = ActiveModelReference.Scan(oScanCriteria)
    Dim oElem As Element
    Dim brokenElements As Collection
    While ee.MoveNext
        Set oElem = ee.Current
        If oElem.IsLineElement And Not oElem.Level Is Nothing Then
            If oElem.Level.name <> "Level 63" Then
                If IsIntersecting(oElem.AsIntersectableElement, boundaries) Then
                    Set brokenElements = BreakElementVerticies(oElem)
                    For i = 1 To brokenElements.Count
                        ActiveModelReference.AddElement brokenElements.Item(i)
                    Next i
                    ActiveModelReference.RemoveElement oElem
                End If
            End If
        ElseIf oElem.IsShapeElement Then
            If oElem.Level.name <> "Level 63" Then
                If IsIntersecting(oElem.AsIntersectableElement, boundaries) Then
                    Set brokenElements = BreakElementVerticies(oElem)
                    For i = 1 To brokenElements.Count
                        ActiveModelReference.AddElement brokenElements.Item(i)
                    Next i
                    ActiveModelReference.RemoveElement oElem
                End If
            End If
        End If
    Wend
End Function

Function IsIntersecting(oElem As IntersectableElement, boundaries As Collection) As Boolean
    For i = 1 To boundaries.Count
        If UBound(oElem.GetIntersectionPoints(boundaries.Item(i), Matrix3dIdentity)) <> -1 Then
            IsIntersecting = True
            Exit Function
        End If
    Next i
    IsIntersecting = False
End Function

'Gets the position of the top left corner of the title sheet contents (not the very left)
Function getTitleCorner(titleSheet As Collection) As Point3d
    Dim point As Point3d
    Dim ele As Element
    Dim haveCorner As Boolean
    haveCorner = False
    Dim currCorner As Point3d
    For i = 1 To titleSheet.Count
        Set ele = titleSheet.Item(i)
        If ele.IsComplexShapeElement Then
            If ele.AsComplexShapeElement.Area > 300000 Then
                If ele.Level.name = "Level 63" Then
                    'Map Boundary
                    If haveCorner Then
                        currCorner = getCorner(ele.AsComplexShapeElement)
                        point = FurthestCornerPoint(point, currCorner)
                    Else
                        haveCorner = True
                        point = getCorner(ele.AsComplexShapeElement)
                    End If
                End If
            End If
        End If
    Next i
    If point.X = 0 And point.Y = 0 Then
        MsgBox "Could not find complex shape element in title sheet!" & vbNewLine & "Contents may be at origin."
    End If
    getTitleCorner = point
End Function

Function getCorner(boundary As ComplexShapeElement) As Point3d
    Dim point As Point3d
    Dim ee As ElementEnumerator
    Set ee = boundary.GetSubElements
    ee.Reset
    ee.MoveNext
    Debug.Print ee.Current.Type
    point = FurthestCornerPoint(ee.Current.AsChainableElement.StartPoint, ee.Current.AsChainableElement.EndPoint)
    While ee.MoveNext
        point = FurthestCornerPoint(point, FurthestCornerPoint(ee.Current.AsChainableElement.StartPoint, ee.Current.AsChainableElement.EndPoint))
    Wend
    getCorner = point
End Function

'Returns the point  that is further to the top left
Function FurthestCornerPoint(p1 As Point3d, p2 As Point3d) As Point3d
    Dim xDif As Double
    Dim yDif As Double
    xDif = p1.X - p2.X
    yDif = p1.Y - p2.Y
    If Abs(xDif) > Abs(yDif) Then
        If xDif > 0 Then
            FurthestCornerPoint = p2
        Else
            FurthestCornerPoint = p1
        End If
    Else
        If yDif > 0 Then
            FurthestCornerPoint = p1
        Else
            FurthestCornerPoint = p2
        End If
    End If
    

End Function

'Returns a collection of elements that are within the mapBoundary
Function getClippedElements(mapBoundary As ComplexShapeElement) As Collection
    Dim oFence As Fence
    Dim oElem As Element
    Dim myView As View
    
    
     With ActiveSettings
        .FenceClip = True
    End With

    Set oFence = ActiveDesignFile.Fence
    oFence.Undefine

    Set myView = CommandState.LastView

    oFence.DefineFromElement myView, mapBoundary.AsClosedElement
    'Is this needed?
    oFence.Draw
    'Debug.Print "View: " & oFence.
    'See CopyFenceContents() example to possible implement saving the active settings (probably should do outside this method)
    Dim ee As ElementEnumerator
    Set ee = oFence.GetContents(True)
    
    Dim includedElements As New Collection
    Dim brokenElements As Collection
    
    While ee.MoveNext
        '  ee.Current is returning a copy of the element
        '  because this program called GetContents with
        '  the CloneElements argument set to True.
        
        Set oElem = ee.Current
        ActiveModelReference.RemoveElement oElem
        If Not oElem.Level Is Nothing Then
            If oElem.Level.name = "Exist Property Line" Or oElem.Level.name = "Exist Right of Way Line" Or oElem.Level.name = "Level 10" Then
                Set brokenElements = BreakElementVerticies(oElem)
                For i = 1 To brokenElements.Count
                    includedElements.Add brokenElements.Item(i)
                Next i
            ElseIf oElem.Level.name = "Matchline" And oElem.IsLineElement Then
                'Only add if it hasn't been cut off
                If oElem.AsLineElement.Length > 319 Then
                    includedElements.Add oElem
                End If
            Else
                includedElements.Add oElem
            End If
        Else
            includedElements.Add oElem
        End If
    Wend
    includedElements.Add mapBoundary
    Set getClippedElements = includedElements
End Function

'Break a complex element down to its subelements
Function BreakElementVerticies(oElem As Element) As Collection
    Dim includedElements As New Collection
    Dim points() As Point3d
    Dim newLine As LineElement
    Dim verticies(0 To 1) As Point3d
    Dim subElements As ElementEnumerator
    Dim subElement As Element
    Dim cc As New CopyContext
    cc.AddElementToModel = False
    If oElem.IsComplexStringElement Then
        Set subElements = oElem.AsComplexStringElement.GetSubElements
        While subElements.MoveNext
            Set subElement = ActiveModelReference.CopyElement(subElements.Current, cc)
            includedElements.Add subElement
        Wend
    ElseIf oElem.IsLineElement Then
        points = oElem.AsLineElement.GetVertices
        For i = LBound(points) + 1 To UBound(points)
            verticies(0) = points(i - 1)
            verticies(1) = points(i)
            Set newLine = CreateLineElement1(oElem, verticies)
            includedElements.Add newLine
        Next i
    ElseIf oElem.IsShapeElement Then
        points = oElem.AsShapeElement.GetVertices
        For i = LBound(points) + 1 To UBound(points)
            verticies(0) = points(i - 1)
            verticies(1) = points(i)
            Set newLine = CreateLineElement1(oElem, verticies)
            includedElements.Add newLine
        Next i
    Else
        includedElements.Add oElem
    End If
    Set BreakElementVerticies = includedElements
End Function

Function getAllMapNumbers() As Collection
    
    Dim oScanCriteria As ElementScanCriteria
    Set oScanCriteria = New ElementScanCriteria
    oScanCriteria.ExcludeAllLevels
    oScanCriteria.IncludeLevel ActiveModelReference.Levels("Level 62")
    oScanCriteria.ExcludeAllTypes
    oScanCriteria.IncludeType msdElementTypeText
    oScanCriteria.IncludeType msdElementTypeTextNode
    
    Dim ee As ElementEnumerator
    Set ee = ActiveModelReference.Scan(oScanCriteria)
    
    Dim includedElements As New Collection
    Dim maps() As Map
    Dim currMap As String
    Dim included As Boolean
    While ee.MoveNext
        Dim ele As Element
        Set ele = ee.Current
                Dim textContents As String
                If ele.IsTextElement Then
                    textContents = ele.AsTextElement.text
                Else
                    textContents = ele.AsTextNodeElement.TextLine(1)
                End If
                If InStr(textContents, "MAP-") = 1 Then
                    Dim mapNum As String
                    mapNum = Right(textContents, Len(textContents) - 4)
                    included = False
                    For i = 1 To includedElements.Count
                        currMap = includedElements.Item(i)
                        If currMap = mapNum Then
                            included = True
                            Exit For
                        End If
                    Next i
                    If Not included Then
                        includedElements.Add mapNum
                    End If
                End If
    Wend
    ReDim maps(0 To includedElements.Count - 1)
    For i = 1 To includedElements.Count
        Set maps(i - 1) = New Map
        maps(i - 1).MapNumber = includedElements.Item(i)
    Next i
    Arrays.QuickActionSort maps, 0, includedElements.Count - 1
    Dim sortedNumbers As New Collection
    For i = 1 To includedElements.Count
        'Debug.Print maps(i - 1).MapNumber
        sortedNumbers.Add maps(i - 1).MapNumber
    Next i
    
    Set getAllMapNumbers = sortedNumbers
End Function

'Returns the map boundary elements that are in the current fence
Function getSelectedMapBoundaries() As Collection
    
    Dim oFence As Fence
    Dim oElem As Element
    Dim myView As View
    
     With ActiveSettings
        .FenceClip = False
        .FenceOverlap = True
    End With

    Set oFence = ActiveDesignFile.Fence

    Set myView = CommandState.LastView

    'See CopyFenceContents() example to possible implement saving the active settings (probably should do outside this method)
    Dim ee As ElementEnumerator
    Set ee = oFence.GetContents(True)
    
    Dim includedElements As New Collection
    
    While ee.MoveNext
        Dim ele As Element
        '  ee.Current is returning a copy of the element
        '  because this program called GetContents with
        '  the CloneElements argument set to True.
        Set ele = ee.Current
        If ele.IsComplexShapeElement Then
            If ele.Level.name = "Level 63" Then
                'Check if contents contains an included map number
                Dim inside As Collection
                Set inside = getClippedElements(ele.AsComplexShapeElement)
                Dim oEle As Element
                Dim included As Boolean
                included = True
                If MapFormatForm.MapRange <> "All" Then
                    For i = 1 To inside.Count
                        Set oEle = inside.Item(i)
                        If oEle.IsTextElement Then
                            If oEle.Level.name = "Level 62" Then
                                If Left(oEle.AsTextElement.text, 3) = "MAP" Then
                                    'Debug.Print oEle.AsTextElement.Text
                                    included = isMapIncluded(Right(oEle.AsTextElement.text, Len(oEle.AsTextElement.text) - 4))
                                End If
                            End If
                        End If
                    Next i
                End If
                If included Then
                    includedElements.Add ele.AsComplexShapeElement
                End If
            End If
        End If
    Wend
    Set getSelectedMapBoundaries = includedElements
End Function

'Places a title sheet at a relative location with a changed map number and added road names
Function PlaceTitleSheet(titleSheet As Collection, mapNum As String, roadNames As Collection, moveDistance As Point3d)
    Dim ele As Element
    Dim cc As New CopyContext
    cc.AddElementToModel = False
    'Iterate through titleSheet
    For i = 1 To titleSheet.Count
        Set ele = titleSheet.Item(i)
            Set ele = ActiveModelReference.CopyElement(ele, cc) 'Copy Element
            ele.Move moveDistance 'Move element
        If ele.IsTextNodeElement Then
            If ele.Level.name = "Level 62" Then
                'Modify text node with map number and road names
                If ele.AsTextNodeElement.TextLinesCount > 1 Then
                    'Delete text lines that will be rewritten
                    For j = 0 To ele.AsTextNodeElement.TextLinesCount - 2
                        ele.AsTextNodeElement.DeleteTextLine 2
                    Next j
                End If
                'Create roadString by combining road names together into a list
                Dim roadString As String
                Dim mapString As String
                roadString = ""
                mapString = "MAP " & mapNum
                If roadNames.Count = 1 Then
                    '1 road names
                    roadString = roadNames.Item(1)
                ElseIf roadNames.Count = 2 Then
                    '2 road names (RD & RD)
                    roadString = roadNames.Item(1) & " & " & roadNames.Item(2)
                ElseIf roadNames.Count = 3 Then
                    '3 road names - add one to map line
                    roadString = roadNames.Item(1) & ", " & roadNames.Item(2)
                    mapString = roadNames.Item(3) & "; " & mapString
                ElseIf roadNames.Count > 3 Then
                    'More than 3 - list all on road line (will have to fix manually)
                    Debug.Print "Too many roads on map " & mapNum
                    For j = 1 To roadNames.Count
                        If j <> 1 Then roadString = roadString & ", "
                        roadString = roadString & roadNames.Item(j)
                    Next j
                End If
                
                ele.AsTextNodeElement.AddTextLine roadString 'Add roadString to text line
                ele.AsTextNodeElement.AddTextLine mapString
            End If
        End If
        ActiveModelReference.AddElement ele
        'ele.Rewrite
        ele.Redraw 'Redraw element
    Next i
End Function

'Get map number and delete
'Get complex shape elements on level 63 that aren't full size
'extend containing match lines to their edges
'Check for intersecting lines
'Trim lines
'Record line distances for each side
'Break line a little further than the furthest intersecting element unless it is out of the boundary
'Delete elements on the ousides of the match lines excluding match level and house adresses
'Delete match text that has the same map number

'Formats the map
Public Function FormatMap(originalMap As Map, mapCorner As Point3d, mapMoveDistance As Point3d) As Map
    Dim finalCorner As Point3d
    finalCorner = Point3dAdd(mapCorner, mapMoveDistance)
    Dim mapElements As Collection
    Set mapElements = getClippedElements(originalMap.MainBoundary)
    Dim mapObj As New Map
    Dim processedContents As New Collection
    Dim roadNames As New Collection
    Dim boundaryElements() As ShapeElement
    Dim matchlines() As LineElement
    Dim numMatchlines As Integer
    numMatchlines = 0
    Dim ele As Element
    Dim ele1 As Element
    Dim addEle As Boolean
    Dim textContents As String
    Dim containedElements As Collection
    Dim MainBoundary As ComplexShapeElement
    
    Dim matchCenterPoints As New Collection
    Dim distance As Double
    Dim iPoint As Point3d
    Dim ExcludedLevelsString As String
    Dim ExcludedLevelsArray() As String
    ExcludedLevelsString = CStr(MapFormatForm.ExcludedLevels)
    ExcludedLevelsArray = Split(ExcludedLevelsString, ",", -1, vbTextCompare)
    
    For i = 1 To mapElements.Count
        Set ele = mapElements.Item(i)
        addEle = True
        If Not ele.Level Is Nothing Then
        If ele.IsShapeElement Then
            If ele.Level.name = "Level 63" Then
                If ele.AsShapeElement.Area < 700000 Then
                    'Boundary Element
                    Dim verticies() As Point3d
                    verticies = ele.AsShapeElement.GetVertices
                    'Try to get containing match line
                    For j = 1 To mapElements.Count
                        'Check if it is a match line
                        Set ele1 = mapElements.Item(j)
                        If ele1.IsLineElement And Not ele1.Level Is Nothing Then
                            If ele1.Level.name = "Matchline" Then
                                If LineElementInside(ele.AsShapeElement, ele1.AsLineElement) Then
                                    'Matchline line
                                    numMatchlines = numMatchlines + 1
                                    Dim tempArray() As LineElement
                                    ReDim tempArray(numMatchlines)
                                    For k = 0 To numMatchlines - 2
                                        Set tempArray(k) = matchlines(k)
                                    Next k
                                    ReDim boundaryElements(numMatchlines)
                                    ReDim matchlines(numMatchlines)
                                    For k = 0 To numMatchlines - 2
                                        Set matchlines(k) = tempArray(k)
                                    Next k
                                    Set boundaryElements(numMatchlines - 1) = ele.AsShapeElement
                                    'Trim match lines to border elements
                                    Dim center As Double
                                    Dim beforeIntersection As Double
                                    Dim afterIntersection As Double
                                    Dim intersections() As Point3d
                                    matchCenterPoints.Add ele1.AsLineElement.PointAtDistance(ele1.AsLineElement.Length / 2)
                                    Set ele1 = ExtendLine(ele1, 1300)
                                    center = ele1.AsLineElement.Length / 2
                                    beforeIntersection = 0
                                    afterIntersection = ele1.AsLineElement.Length
                                    intersections = ele1.AsLineElement.GetIntersectionPoints(ele, Matrix3dIdentity)
                                    If UBound(intersections) <> -1 Then
                                        'Has intersection
                                        For k = 0 To UBound(intersections)
                                            iPoint = intersections(k)
                                            distance = ele1.AsLineElement.DistanceAtPoint(iPoint)
                                            'Check if point is closer
                                            If distance > center And distance < afterIntersection Then
                                                afterIntersection = distance
                                            ElseIf distance < center And distance > beforeIntersection Then
                                                beforeIntersection = distance
                                            End If
                                            'Debug.Print "Point: " & iPoint.X & " " & iPoint.Y
                                        Next k
                                    End If
                                    Dim beforePoint As Point3d
                                    Dim afterPoint As Point3d
                                    beforePoint = ele1.AsLineElement.PointAtDistance(beforeIntersection)
                                    afterPoint = ele1.AsLineElement.PointAtDistance(afterIntersection)
                                    'Change verticies at new points
                                    ele1.AsLineElement.ModifyVertex 0, beforePoint
                                    ele1.AsLineElement.ModifyVertex ele1.AsLineElement.VerticesCount - 1, afterPoint
            
                                    Set matchlines(numMatchlines - 1) = ele1.AsLineElement
                                    Exit For
                                End If
                            End If
                        End If
                    Next j
                End If
                addEle = False
            End If
        ElseIf ele.IsComplexShapeElement Then
            If ele.Level.name = "Level 63" Then
                Set MainBoundary = ele.AsComplexShapeElement
            End If
        ElseIf ele.IsLineElement Then
            If ele.Level.name = "Matchline" Then
                'Matchline line
                addEle = False
            End If
        ElseIf ele.IsTextElement Then
            If ele.Level.name = "Level 62" Then
                'Map Number
                If mapObj.MapNumber <> "0" Then
                    Debug.Print "Found multiple map numbers in the same frame: Map-" & mapObj.MapNumber
                    MsgBox "Found multiple map numbers in the same frame: Map-" & mapObj.MapNumber & vbNewLine & "Please fix and run the program again.", vbCritical, "Formatting Error"
                    End
                End If
                textContents = Right(ele.AsTextElement.text, Len(ele.AsTextElement.text) - 4) 'Get the right number of the map
                mapObj.MapNumber = textContents
                Debug.Print "Formatting: " & mapObj.MapNumber
                addEle = False 'Will not be keeping this
            ElseIf ele.Level.name = "Exist Roads EOP Text" Then
                'Road Name
                textContents = Split(ele.AsTextElement.text, "  ")(0)
                Dim contains As Boolean
                contains = False
                'Check if roadName Exists
                For j = 1 To roadNames.Count
                    If roadNames.Item(j) = textContents Then
                        contains = True
                        Exit For
                    End If
                Next j
                If isStateRoad(textContents) Then
                    If Not contains Then
                        'Add to roadNames
                        roadNames.Add textContents
                    End If
                End If
            End If
        ElseIf ele.IsTextNodeElement Then
            If ele.Level.name = "Exist Roads EOP Text" Then
                'Road Name
                textContents = Split(ele.AsTextNodeElement.TextLine(1), "  ")(0)
                Dim contains2 As Boolean
                contains2 = False
                'Check if roadName Exists
                For j = 1 To roadNames.Count
                    If roadNames.Item(j) = textContents Then
                        contains2 = True
                        Exit For
                    End If
                Next j
                If isStateRoad(textContents) Then
                    If Not contains2 Then
                        'Add to roadNames
                        roadNames.Add textContents
                    End If
                End If
            End If
        End If
        End If
        'Remove specific levels
        If ele.IsGraphical Then
            If Not ele.Level Is Nothing Then
                'Check if it is a level to remove
                For j = LBound(ExcludedLevelsArray, 1) To UBound(ExcludedLevelsArray, 1)
                    If ele.Level.name = ExcludedLevelsArray(j) Then
                        addEle = False
                    End If
                Next j
            End If
        End If
        
        If addEle Then
            processedContents.Add ele
        End If
    Next i
    
    
    mapObj.SetRoadNames roadNames
    
    'Clear old map elements
    For i = 1 To mapElements.Count
        mapElements.remove 1
    Next i
    
    'Debug.Print "Match Lines: " & numMatchlines
    'Will have to keep track of furthest intersections for these match lines
    Dim furthestMatchIntersectionAfter() As Double
    Dim furthestMatchIntersectionBefore() As Double
    ReDim furthestMatchIntersectionAfter(numMatchlines)
    ReDim furthestMatchIntersectionBefore(numMatchlines)
    For i = 0 To numMatchlines - 1
        iPoint = matchCenterPoints.Item(i + 1)
        distance = matchlines(i).DistanceAtPoint(iPoint)
        furthestMatchIntersectionAfter(i) = distance + 160
        furthestMatchIntersectionBefore(i) = distance - 160
    Next i
    
    Dim corner As Point3d
    corner = MapFormatModule.getCorner(MainBoundary)
    Dim matchTexts As New Collection
    Dim moveDistance As Point3d
    moveDistance = Point3dSubtract(finalCorner, corner)
    
    
    Dim cutoutBoundaries() As ShapeElement
    ReDim cutoutBoundaries(numMatchlines)
    
    For i = 0 To numMatchlines - 1
        Set cutoutBoundaries(i) = CreateDeletionBoundary(matchlines(i), MainBoundary)
        cutoutBoundaries(i).Move moveDistance
    Next i
    
    Dim cc As New CopyContext
    ' Remove match text
    For i = 1 To processedContents.Count
        Set ele = processedContents.Item(i)
        Dim copyEle As Element
        Dim isMatchText As Boolean
        isMatchText = False
        'Remove half of match line text
        If Not ele.Level Is Nothing Then
            If ele.IsTextElement Or ele.IsTextNodeElement Then
                If ele.Level.name = "Matchline" Then
                    'Matchline
                    If ele.IsTextElement Then
                        textContents = Right(ele.AsTextElement.text, Len(ele.AsTextElement.text) - 25) 'Get the right most number of the match text
                    ElseIf ele.IsTextNodeElement Then
                        textContents = Right(ele.AsTextNodeElement.TextLine(1), Len(ele.AsTextNodeElement.TextLine(1)) - 25)
                    End If
                    'Debug.Print textContents
                    If textContents <> mapObj.MapNumber Then
                        'Debug.Print "Including match text for map " & textContents
                        Set copyEle = ActiveModelReference.CopyElement(ele, cc)
                        matchTexts.Add copyEle
                    End If
                    isMatchText = True
                End If
            End If
        End If
        
        If Not isMatchText Then
            'Move element
            Set copyEle = ActiveModelReference.CopyElement(ele, cc)
            copyEle.Move moveDistance
            copyEle.Redraw
            copyEle.Rewrite
        End If
    Next i
    
    
    Dim addedElements As Collection 'This is now matchline intersections only
    'processedContents and machlines have not been moved over yet
    Set addedElements = CutElement(processedContents, matchlines, numMatchlines, cutoutBoundaries)
    
    Dim intersectionDistancesBefore As Variant
    Dim intersectionDistancesAfter As Variant
    'First items are intersection distances
    intersectionDistancesBefore = addedElements.Item(1)
    intersectionDistancesAfter = addedElements.Item(2)
    'Update furthest distances
    For j = 0 To numMatchlines - 1
        distance = intersectionDistancesBefore(j)
        If distance <> -1 Then
            If distance < furthestMatchIntersectionBefore(j) Then
                furthestMatchIntersectionBefore(j) = distance
            End If
        End If
        distance = intersectionDistancesAfter(j)
        If distance <> -1 Then
            If distance > furthestMatchIntersectionAfter(j) Then
                furthestMatchIntersectionAfter(j) = distance
            End If
        End If
    Next j
    
    'Move match text over
    For j = 1 To matchTexts.Count
        Set ele = matchTexts.Item(j)
        ele.Move moveDistance
        ele.Redraw
        ele.Rewrite
    Next j
    
    'Trim match lines
    For i = 0 To numMatchlines - 1
        Set ele1 = ActiveModelReference.CopyElement(matchlines(i), cc)
        beforePoint = ele1.AsLineElement.PointAtDistance(Max(furthestMatchIntersectionBefore(i) - 30, 0))
        afterPoint = ele1.AsLineElement.PointAtDistance(Min(furthestMatchIntersectionAfter(i) + 30, ele1.AsLineElement.Length))
        'Change verticies at new points
        ele1.AsLineElement.ModifyVertex 0, beforePoint
        ele1.AsLineElement.ModifyVertex ele1.AsLineElement.VerticesCount - 1, afterPoint
        
        ele1.Move moveDistance
        ele1.Rewrite
        ele1.Redraw
    Next i

    'Set corner point
    mapObj.CornerPoint = finalCorner
    
    If MapFormatForm.ChangeToWhite Then
        TurnWhite MainBoundary, moveDistance
    End If
    
    If MapFormatForm.CopyRaster Then
        ' Copy raster
        RasterModule.MoveAndClip corner, moveDistance, originalMap.GetOriginalBoundary(), mapObj.MapNumber
    End If
    
    Set FormatMap = mapObj
End Function

Function TurnWhite(boundary As ComplexShapeElement, moveDistance As Point3d)
    Dim cc As New CopyContext
    cc.AddElementToModel = False
    Dim movedBoundary As ComplexShapeElement
    Set movedBoundary = ActiveModelReference.CopyElement(boundary, cc)
    movedBoundary.Move moveDistance
    
    Dim oFence As Fence
    Dim ele As Element
    Dim myView As View
    
    
     With ActiveSettings
        .FenceClip = False
        .FenceOverlap = True
    End With

    Set oFence = ActiveDesignFile.Fence
    oFence.Undefine

    Set myView = CommandState.LastView

    oFence.DefineFromElement myView, movedBoundary
    'Is this needed?
    oFence.Draw
    'Debug.Print "View: " & oFence.
    'See CopyFenceContents() example to possible implement saving the active settings (probably should do outside this method)
    Dim ee As ElementEnumerator
    Set ee = oFence.GetContents(False)
    While ee.MoveNext
        Set ele = ee.Current
        If ele.IsGraphical Then
            If ele.IsCellElement Then
                'Check cell name for color change
                If ele.AsCellElement.name <> "EXIST UTILITIES TELEPHONE HAND HOLE" And ele.AsCellElement.name <> "EXIST UTILITIES TV PEDESTAL" Then
                    'Change to white
                    ele.AsCellElement.Color = 0
                End If
            ElseIf Not ele.Level Is Nothing Then
                'Check levels for color change
                If MapFormatForm.CopyRaster And (ele.IsTextElement Or ele.IsTextNodeElement Or ele.IsDimensionElement) Then
                    ele.Color = CInt(MapFormatForm.RasterTextColor)
                    If ele.IsDimensionElement And ele.Level.name = "Exist Right of Way Width CELL" Then
                        'Extract style to change all elements to white
                        Set oDimStyle = ele.AsDimensionElement.DimensionStyle
                        oDimStyle.OverallColor = 0
                        oDimStyle.OverrideExtensionLineColor = True
                        oDimStyle.ExtensionLineColor = 0
                        ele.AsDimensionElement.DimensionStyle = oDimStyle
                    End If
                ElseIf ele.Level.name <> "Level 30" And ele.Level.name <> "CATV Line UBO Text" And ele.Level.name <> "Level 12" And Not IsBorePit(ele) Then
                    'Change to white
                    ele.Color = 0
                    If ele.IsDimensionElement And ele.Level.name = "Exist Right of Way Width CELL" Then
                        'Extract style to change all elements to white
                        Set oDimStyle = ele.AsDimensionElement.DimensionStyle
                        oDimStyle.OverallColor = 0
                        oDimStyle.OverrideExtensionLineColor = True
                        oDimStyle.ExtensionLineColor = 0
                        ele.AsDimensionElement.DimensionStyle = oDimStyle
                    End If
                End If
            End If
        End If
        ele.Rewrite
        ele.Redraw
        If ele.IsComplexShapeElement Or ele.IsShapeElement Then
            If ele.Level.name = "Level 63" Then
                ActiveModelReference.RemoveElement ele
            End If
        End If
    Wend
End Function

' Check if an element is a bore pit. Sometimes microstation can glitch out and return an empty level name.
'
' @param oElem  Element to check
' @returns      true if the element is a bore pit.
Function IsBorePit(oElem As Element) As Boolean
    If Not oElem Is Nothing Then
     If oElem.IsComplexShapeElement And Not oElem.Level Is Nothing Then
        If oElem.Level.name = "Level 12" Or (oElem.Level.name = "" And oElem.AsComplexShapeElement.ApparentColor(CommandState.LastView) = 87 And oElem.AsComplexShapeElement.Area() < 20) Then
            IsBorePit = True
            Exit Function
        End If
     End If
    End If
    IsBorePit = False
End Function

'Cuts an element that is on the wrong side of a match line
'Returns a collection of elements to add to the model
Function CutElement(addedElements As Collection, matchlines() As LineElement, numMatchlines As Integer, cutoutBoundaries() As ShapeElement) As Collection
    'Debug.Print "Cutting Element"
    Dim elementProcessor As New Collection
    Dim ele As Element
    Dim ele1 As LineElement
    Dim intersectionDistancesBefore() As Double
    ReDim intersectionDistancesBefore(numMatchlines)
    Dim intersectionDistancesAfter() As Double
    ReDim intersectionDistancesAfter(numMatchlines)
    Dim distance As Double
    Dim iPoint As Point3d
    Dim beforeBreak As Element
    Dim afterBreak As Element
    Dim intersections1() As Point3d

    'Break lines intersecting match lines
    For j = 0 To numMatchlines - 1
        intersectionDistancesBefore(j) = -1
        intersectionDistancesAfter(j) = -1
        Set ele1 = matchlines(j)
        'Create boundary for elements to cut out
        Dim cutout As ShapeElement
        Set cutout = cutoutBoundaries(j)
        'Clear old elements
        Set elementProcessor = Nothing
        'Debug.Print "Elements to process: " & addedElements.Count
        For i = 1 To addedElements.Count
            Set ele = addedElements.Item(i)
            'check if element intersects the match line
            If ele.IsChainableElement And Not ele.Level Is Nothing Then
                If ele.Level.name <> "Matchline" Then
                    intersections1 = ele1.GetIntersectionPoints(ele, Matrix3dIdentity)
                    If UBound(intersections1) <> -1 Then
                        'Has intersection
                        For k = 0 To UBound(intersections1)
                            iPoint = intersections1(k)
                            distance = ele1.DistanceAtPoint(iPoint)
                            Dim distanceBefore As Double
                            Dim distanceAfter As Double
                            If ele.Level.name = "Exist Right of Way Line" Then
                                distanceBefore = distance - 70
                                distanceAfter = distance + 70
                            Else
                                distanceBefore = distance
                                distanceAfter = distance
                            End If
                            If intersectionDistancesBefore(j) = -1 Or intersectionDistancesBefore(j) > distanceBefore Then
                                intersectionDistancesBefore(j) = distanceBefore
                            End If
                            If intersectionDistancesAfter(j) = -1 Or intersectionDistancesAfter(j) < distanceAfter Then
                                intersectionDistancesAfter(j) = distanceAfter
                            End If
                            'Debug.Print "Point: " & iPoint.X & " " & iPoint.Y
                        Next k
                    End If
                End If
            End If
        Next i
        
        'Reset added elements with only the ones that made it past
        RemoveInside cutout
        
    Next j
    'Add intersection distances to start
    Dim finalElements As New Collection
    finalElements.Add intersectionDistancesBefore
    finalElements.Add intersectionDistancesAfter
    Set CutElement = finalElements
End Function

'Removes any elements inside the cutout from the active model reference
'Returns any remaining elements
Function RemoveInside(cutout As ShapeElement)
    Dim oFence As Fence
    Dim oElem As Element
    Dim myView As View
    
    
     With ActiveSettings
        .FenceClip = True
        .FenceOverlap = False
    End With

    Set oFence = ActiveDesignFile.Fence
    oFence.Undefine

    Set myView = CommandState.LastView

    oFence.DefineFromElement myView, cutout
    'Is this needed?
    oFence.Draw
    'Debug.Print "View: " & oFence.
    'See CopyFenceContents() example to possible implement saving the active settings (probably should do outside this method)
    Dim ee As ElementEnumerator
    Set ee = oFence.GetContents(False)
    'Debug.Print "Checking elements to remove"
    While ee.MoveNext
        ActiveModelReference.RemoveElement ee.Current
    Wend
End Function

Function Max(num1 As Double, num2 As Double) As Double
    If num1 > num2 Then
        Max = num1
        Exit Function
    End If
    Max = num2
End Function

Function Min(num1 As Double, num2 As Double) As Double
    If num1 < num2 Then
        Min = num1
        Exit Function
    End If
    Min = num2
End Function

'Create a boundary from the match line to the edge of the main boundary
Function CreateDeletionBoundary(matchline As LineElement, MainBoundary As ComplexShapeElement) As ShapeElement
    Dim biasPoint As Point3d
    Dim matchCenter As Point3d
    matchCenter = matchline.PointAtDistance(matchline.Length / 2)
    biasPoint = Point3dAdd(matchCenter, Point3dScale(Point3dNormalize(Point3dSubtract(matchCenter, MainBoundary.Centroid)), 100))
    Dim point1 As Point3d
    Dim point2 As Point3d
    point1 = MainBoundary.ProjectPointOnPerpendicular1(matchline.StartPoint, biasPoint, Matrix3dIdentity)
    point2 = MainBoundary.ProjectPointOnPerpendicular1(matchline.EndPoint, biasPoint, Matrix3dIdentity)
    'mainBoundary to verticies
    Dim mainVerticies(0 To 4) As Point3d
    Dim ee As ElementEnumerator
    Set ee = MainBoundary.GetSubElements
    For i = 0 To 3
        ee.MoveNext
        mainVerticies(i) = ee.Current.AsLineElement.StartPoint
    Next i
    mainVerticies(4) = mainVerticies(0)
    'find where projected points lie between verticies
    'The indicies represent the index of the point before them
    Dim p1Index As Integer
    Dim p2Index As Integer
    For i = 1 To 4
        If Abs(Point3dDistance(mainVerticies(i), mainVerticies(i - 1)) - Point3dDistance(mainVerticies(i), point1) - Point3dDistance(mainVerticies(i - 1), point1)) < 1 Then
            'point1 is between points
            p1Index = i - 1
        End If
        If Abs(Point3dDistance(mainVerticies(i), mainVerticies(i - 1)) - Point3dDistance(mainVerticies(i), point2) - Point3dDistance(mainVerticies(i - 1), point2)) < 1 Then
            'point2 is between points
            p2Index = i - 1
        End If
    Next i
    'construct shapes with point between verticies
    Dim shape1Verticies As New Collection
    Dim shape2Verticies As New Collection
    Dim inShape1 As Boolean 'This records the direction of iteration
    inShape1 = True
    For i = 0 To 3
        If inShape1 Then
            'Add to shape 1
            shape1Verticies.Add mainVerticies(i)
        Else
            'Add to shape 2
            shape2Verticies.Add mainVerticies(i)
        End If
        
        If p1Index = i Or p2Index = i Then
            inShape1 = Not inShape1
            'Add point to both shapes
            If p1Index = i Then
                shape1Verticies.Add point1
                shape2Verticies.Add point1
                If inShape1 Then
                    shape2Verticies.Add matchline.StartPoint
                    shape2Verticies.Add matchline.EndPoint
                Else
                    shape1Verticies.Add matchline.StartPoint
                    shape1Verticies.Add matchline.EndPoint
                End If
            Else
                'Start shape 2
                shape1Verticies.Add point2
                shape2Verticies.Add point2
                If Not inShape1 Then
                    'Clockwise
                    shape1Verticies.Add matchline.EndPoint
                    shape1Verticies.Add matchline.StartPoint
                Else
                    'Counterclockwise
                    shape2Verticies.Add matchline.EndPoint
                    shape2Verticies.Add matchline.StartPoint
                End If
            End If
        End If
    Next i
    'Create shapes
    Dim shape1 As ShapeElement
    Dim shape2 As ShapeElement
    Dim verticies() As Point3d
    If shape1Verticies.Count > 2 Then
        ReDim verticies(0 To shape1Verticies.Count)
        'Debug.Print "Create shape 1"
        For i = 0 To shape1Verticies.Count - 1
            verticies(i) = shape1Verticies.Item(i + 1)
            'Debug.Print verticies(i).X & " " & verticies(i).Y
        Next i
        verticies(shape1Verticies.Count) = shape1Verticies.Item(1)
    Else
        'Invalid shape - matchline invalid
        ReDim verticies(0 To 3)
        verticies(0) = Point3dFromXY(0, 0)
        verticies(1) = Point3dFromXY(1, 0)
        verticies(2) = Point3dFromXY(0, 2)
        verticies(3) = Point3dFromXY(0, 0)
    End If
    Set shape1 = CreateShapeElement1(Nothing, verticies)
    If shape2Verticies.Count > 2 Then
        ReDim verticies(0 To shape2Verticies.Count)
        'Debug.Print "Create shape 2"
        For i = 0 To shape2Verticies.Count - 1
            verticies(i) = shape2Verticies.Item(i + 1)
            'Debug.Print verticies(i).X & " " & verticies(i).Y
        Next i
        verticies(shape2Verticies.Count) = shape2Verticies.Item(1)
    Else
        'Invalid shape - matchline invalid
        ReDim verticies(0 To 3)
        verticies(0) = Point3dFromXY(0, 0)
        verticies(1) = Point3dFromXY(1, 0)
        verticies(2) = Point3dFromXY(0, 2)
        verticies(3) = Point3dFromXY(0, 0)
    End If
    Set shape2 = CreateShapeElement1(Nothing, verticies)
    
    'use least area
    
    If shape1.Area < shape2.Area Then
        Set CreateDeletionBoundary = shape1
    Else
        Set CreateDeletionBoundary = shape2
    End If
    
End Function

'Returns an extended line by length on both sides
Private Function ExtendLine(original As LineElement, Length As Double) As LineElement
    Dim el As LineElement
    Set el = original.Clone

    'Extend start
    Dim segmentVector As Point3d
    segmentVector = Point3dSubtract(el.Vertex(1), el.Vertex(2))
    segmentVector = Point3dNormalize(segmentVector)
    segmentVector = Point3dScale(segmentVector, Length)
    
    Dim newStartPoint As Point3d
    newStartPoint = Point3dAdd(el.Vertex(1), segmentVector)
    el.ModifyVertex 0, newStartPoint
    
    'Extend end
    Dim numOfVertices As Integer
    numOfVertices = el.VerticesCount
    
    segmentVector = Point3dSubtract(el.Vertex(numOfVertices), el.Vertex(numOfVertices - 1))
    segmentVector = Point3dNormalize(segmentVector)
    segmentVector = Point3dScale(segmentVector, Length)
    
    Dim newEndPoint As Point3d
    newEndPoint = Point3dAdd(el.Vertex(numOfVertices), segmentVector)
    el.ModifyVertex numOfVertices - 1, newEndPoint
    
    Set ExtendLine = el
End Function


Private Function LineElementInside(boundary As ShapeElement, ele As LineElement) As Boolean
    Dim verticies() As Point3d
    verticies = boundary.GetVertices
    
    Dim xMax As Double
    Dim xMin As Double
    Dim yMax As Double
    Dim yMin As Double
    xMax = verticies(0).X
    xMin = verticies(0).X
    yMax = verticies(0).Y
    yMin = verticies(0).Y
    If xMax = 0 Then
        Debug.Print "0 point should not be 0"
    End If
    For i = 1 To UBound(verticies)
        If verticies(i).X <> 0 Then
            If verticies(i).X > xMax Then
                xMax = verticies(i).X
            End If
            If verticies(i).X < xMin Then
                xMin = verticies(i).X
            End If
            If verticies(i).Y > yMax Then
                yMax = verticies(i).Y
            End If
            If verticies(i).Y < yMin Then
                yMin = verticies(i).Y
            End If
        End If
    Next i
    Const variability As Double = 0.01
    Dim point As Point3d
    point = ele.StartPoint
    If point.X - variability > xMin And point.X + variability < xMax And point.Y - variability > yMin And point.Y + variability < yMax Then
        ' point good
    Else
        LineElementInside = False
        Exit Function
    End If
    point = ele.EndPoint
    If point.X + variability > xMin And point.X - variability < xMax And point.Y + variability > yMin And point.Y - variability < yMax Then
        ' point good
    Else
        LineElementInside = False
        Exit Function
    End If
    LineElementInside = True
End Function

Private Function onEdge(verticies() As Point3d, point As Point3d) As Boolean
    Dim xMax As Double
    Dim xMin As Double
    Dim yMax As Double
    Dim yMin As Double
    xMax = verticies(0).X
    xMin = verticies(0).X
    yMax = verticies(0).Y
    yMin = verticies(0).Y
    If xMax = 0 Then
        Debug.Print "0 point should not be 0"
    End If
    For i = 1 To UBound(verticies)
        If verticies(i).X <> 0 Then
            If verticies(i).X > xMax Then
                xMax = verticies(i).X
            End If
            If verticies(i).X < xMin Then
                xMin = verticies(i).X
            End If
            If verticies(i).Y > yMax Then
                yMax = verticies(i).Y
            End If
            If verticies(i).Y < yMin Then
                yMin = verticies(i).Y
            End If
        End If
    Next i
    Const variability As Double = 0.01
    If Abs(point.X - xMin) < variability Or Abs(point.X - xMax) < variability Or Abs(point.Y - yMin) < variability Or Abs(point.Y - yMax) < variability Then
        onEdge = True
    Else
        onEdge = False
    End If
End Function

'Mode:
'1 - set
'2 - add
'3 - remove
Sub SetRange(mode As Integer)
    Debug.Print "Setting Format Range"
    'Get starting element from selection
    Dim ee As ElementEnumerator
    If MapFormatForm.UseFence Then
        If ActiveDesignFile.Fence.IsDefined Then
            Set ee = ActiveDesignFile.Fence.GetContents
        Else
            MapFormatForm.MapRange.text = "All"
            Exit Sub
        End If
            
    Else
        Set ee = ActiveModelReference.GetSelectedElements 'Selected elements
    End If
    ee.Reset
    Dim oElem As Element
    Dim numbers As New Collection
    While ee.MoveNext
        Set oElem = ee.Current
        If oElem.IsTextElement Then
            If oElem.Level.name = "Level 62" Then
                If Left(oElem.AsTextElement.text, 3) = "MAP" Then
                    numbers.Add Right(oElem.AsTextElement.text, Len(oElem.AsTextElement.text) - 4)
                End If
            End If
        End If
    Wend
    Dim includedMaps As String
    If mode = 1 Then
    'Set
    includedMaps = ""
    For i = 1 To numbers.Count
        If i <> 1 Then includedMaps = includedMaps & ","
        includedMaps = includedMaps & CStr(numbers.Item(i))
    Next i
    ElseIf mode = 2 Then
        'Add
        If MapFormatForm.MapRange = "All" Then
            includedMaps = ""
        Else
            includedMaps = MapFormatForm.MapRange
        End If
        For i = 1 To numbers.Count
            If Not containsMapNum(includedMaps, numbers.Item(i)) Then
                If includedMaps <> "" Then includedMaps = includedMaps & ","
                includedMaps = includedMaps & numbers.Item(i)
            End If
        Next i
    ElseIf mode = 3 Then
        'Remove
        includedMaps = ""
        Dim currentMaps() As String
        currentMaps = Split(MapFormatForm.MapRange, ",")
        Dim mapNum As String
        Dim remove As Boolean
        For i = 0 To UBound(currentMaps)
            mapNum = currentMaps(i)
            remove = False
            For j = 1 To numbers.Count
                If numbers.Item(j) = mapNum Then
                    remove = True
                    Exit For
                End If
            Next j
            If Not remove Then
                If includedMaps <> "" Then includedMaps = includedMaps & ","
                includedMaps = includedMaps & mapNum
            End If
        Next i
    End If
    
    If includedMaps = "" Then
        MapFormatForm.MapRange.text = "All"
    Else
        MapFormatForm.MapRange.text = includedMaps
    End If
    
    
End Sub

Function isMapIncluded(mapNum As String) As Boolean
    If MapFormatForm.MapRange = "All" Then
        isMapIncluded = True
    Else
        isMapIncluded = containsMapNum(MapFormatForm.MapRange, mapNum)
    End If
End Function

Function containsMapNum(range As String, mapNum As String)
    Dim formatString As String
    formatString = "," & range & ","
    Dim formatNum As String
    formatNum = "," & mapNum & ","
    containsMapNum = InStr(formatString, formatNum) <> 0
End Function

Function isStateRoad(textContents As String) As Boolean
    If InStr(textContents, "SR") = 1 _
    Or InStr(textContents, "NC") = 1 _
    Or InStr(textContents, "US") = 1 _
    Or InStr(textContents, "MU") = 1 _
    Or InStr(textContents, "MD") = 1 _
    Or InStr(textContents, "CO") = 1 _
    Then
        isStateRoad = True
    Else
        isStateRoad = False
    End If
End Function

Attribute VB_Name = "ProgressBar"
Function CreateForm()
    Load ProgressForm
    With ProgressForm
        .StartUpPosition = 0
        .Left = Application.LeftPosition + (0.5 * Application.Width) - (0.5 * .Width)
        .Top = Application.TopPosition + (0.5 * Application.Height) - (0.5 * .Height)
        .Show vbModeless
    End With
End Function

Function UpdateProgress(CurrNum As Integer, TargetNum As Integer, percentProgress As Double)
    Dim displayProgress As Integer
    displayProgress = CInt(percentProgress * 100)
    With ProgressForm
        .FrameProgress.Caption = displayProgress & "% (" & CurrNum & "/" & TargetNum & ")"
        .LabelProgress.Width = percentProgress * (.FrameProgress.Width - 15) + 1
        .Repaint
    End With
    DoEvents
End Function

Function WriteMessage(msg As String)
    ProgressForm.FrameProgress.Caption = msg
    ProgressForm.Repaint
    DoEvents
End Function

Attribute VB_Name = "RasterModule"
Const viewNum As Integer = 8
Dim viewShown As Boolean
Dim printActivated As Boolean

Function Test()
    Dim origin As Point3d
    Dim mapBoundary As ComplexShapeElement
    Dim moveDistance As Point3d
    
    Dim ee As ElementEnumerator
    Set ee = ActiveModelReference.GetSelectedElements()
    ee.MoveNext
    Set mapBoundary = ee.Current.AsComplexShapeElement
    origin = MapFormatModule.getCorner(mapBoundary)
    moveDistance = Point3dFromXY(1000, 1000)
    'MoveAndClip origin, moveDistance, mapBoundary
    ExportImage mapBoundary, "tt"
End Function

Function initialize()
    printActivated = False
End Function

' Must Inherit GeoCS From Model
Function MoveAndClip(origin As Point3d, moveDistance As Point3d, mapBoundary As ComplexShapeElement, mapNum As String)

    Dim rasterAttachment As raster
    Dim geoRef As GeoReferenceInformation
    Dim newOrigin As Point3d
    
    Set rasterAttachment = GetRaster(origin)
    
    If rasterAttachment Is Nothing Then
        MsgBox "No Raster Found"
        Exit Function
    End If
    
    Dim duplicatedAttachment As raster
    If Not printActivated Then
        Set duplicatedAttachment = DuplicateRaster(rasterAttachment)
        
        If duplicatedAttachment Is Nothing Then
            ' Cannot copy raster
            Debug.Print "Cannot Copy Raster"
            BeginImageExport
            MoveAndClip origin, moveDistance, mapBoundary, mapNum
            Exit Function
        End If
        
        moveDistance = Point3dAdd(moveDistance, Point3dFromXY(0.9198, -0.6577)) ' Slightly off for some reason
        newOrigin = Point3dAdd(rasterAttachment.GeoReferenceInformation.origin, moveDistance)
        
        duplicatedAttachment.GeoReferenceInformation.origin = newOrigin
        
        Dim clipBoundaryEle As ComplexShapeElement
        Set clipBoundaryEle = mapBoundary.Clone
        clipBoundaryEle.Move moveDistance
        duplicatedAttachment.SetClipBoundary clipBoundaryEle
    Else
        Set duplicatedAttachment = PrintAndAddRaster(mapBoundary, mapNum, rasterAttachment)
    
        ' Move inside the title sheet. The raster origin is bottom left, so the height has to be subtracted
        duplicatedAttachment.GeoReferenceInformation.origin = Point3dSubtract(Point3dAdd(origin, moveDistance), Point3dFromXY(0, mapBoundary.range.High.Y - mapBoundary.range.Low.Y))
    End If
    
    
    duplicatedAttachment.Reload

End Function

Function GetRaster(oPoint As Point3d) As raster
    Dim obtained As raster
    Set obtained = RasterManager.Rasters.FindRasterInView(oPoint, CommandState.LastView)
    If obtained Is Nothing Then
        Set obtained = RasterManager.Rasters.Find("http://www.bing.com/maps/Aerial")
    End If
    If obtained Is Nothing Then
        Set obtained = RasterManager.Rasters.Item(1)
    End If
    Set GetRaster = obtained
End Function

Function DuplicateRaster(rasterAttachment As raster) As raster
    Dim fileAccess As MsdFileAccessMode
    If rasterAttachment.RasterInformation.IsReadOnly Then
        fileAccess = msdFileAccessModeRead
    Else
        fileAccess = msdFileAccessModeReadWrite
    End If
    Dim newRaster As raster
    On Error GoTo failDuplicate
    Set newRaster = RasterManager.Rasters.Attach(rasterAttachment.RasterInformation.FileNameExploded, msdViewAll, rasterAttachment.ExtendedInformation.attachMode, fileAccess, rasterAttachment.ExtendedInformation.logicalName, rasterAttachment.ExtendedInformation.description)
    newRaster.GeoReferenceInformation.Extent = rasterAttachment.GeoReferenceInformation.Extent
    Set DuplicateRaster = newRaster
    Exit Function
failDuplicate:
    Set DuplicateRaster = Nothing
End Function

' must begin image export before using
Function PrintAndAddRaster(mapBoundary As ComplexShapeElement, mapNum As String, rasterAttachment As raster) As raster
    Dim fileName As String
    Dim folderPath As String
    folderPath = ActiveDesignFile.Path & "\rasters"
    If Dir(folderPath, vbDirectory) = "" Then
        MkDir folderPath
    End If
    
    fileName = folderPath & "\" & mapNum & ".jpg"
    
    ' Check Raster Level
    Dim ele As Element
    Dim rasterLevel As Level
    Set rasterLevel = GetRasterLevel()
    Set ele = RasterManager.Rasters.GetElementFromRaster(rasterAttachment)
    
    If Not ele.Level Is Nothing Then
        If ele.Level.name <> rasterLevel.name Then
            Set ele.Level = rasterLevel
            ele.Rewrite
            ele.Redraw
        End If
    Else
        Set ele.Level = rasterLevel
        ele.Rewrite
        ele.Redraw
    End If
    
    
    ExportImage mapBoundary, fileName
    
    Dim newRaster As raster
    Set newRaster = RasterManager.Rasters.Attach(fileName, msdViewAll, msdAttachReference, msdFileAccessModeRead, "", "")
    newRaster.GeoReferenceInformation.Extent = Point2dFromXY(mapBoundary.range.High.X - mapBoundary.range.Low.X, mapBoundary.range.High.Y - mapBoundary.range.Low.Y)
    Set PrintAndAddRaster = newRaster
End Function

Function BeginImageExport()
    Dim myView As View
    Set myView = ActiveDesignFile.views.Item(viewNum)
    viewShown = myView.IsOpen
    
    CadInputQueue.SendKeyin "DIALOG PLOT" ' Open Print Dialog
    CadInputQueue.SendKeyin "PRINT DRIVER jpeg.pltcfg" ' C:\Program Files\Bentley\MicroStation 2024\MicroStation\Default\pltcfg\jpeg.pltcfg
    CadInputQueue.SendKeyin "PRINT PAPERNAME ANSI D"
    
    ' Get view in place
    myView.IsOpen = True
    myView.SetToFront
    myView.rotation = Matrix3dIdentity
    myView.Maximize
    
    printActivated = True
End Function

Function EndImageExport()
    If printActivated Then
        Dim myView As View
        Set myView = ActiveDesignFile.views.Item(viewNum)
        myView.Restore
        myView.IsOpen = viewShown
        printActivated = False
    End If
End Function

Function ExportImage(mapBoundary As ComplexShapeElement, filePath As String)
    Dim myView As View
    Set myView = ActiveDesignFile.views.Item(viewNum)
    ActiveDesignFile.Fence.DefineFromElement myView, mapBoundary
    FitBoundary mapBoundary, myView
    
    ' Hide Levels
    Dim rasterLevel As Level
    Set rasterLevel = GetRasterLevel()
    For i = 1 To ActiveDesignFile.Levels.Count
        myView.HideLevel ActiveDesignFile.Levels(i)
    Next i
    myView.ShowLevel rasterLevel
    
    myView.Redraw
    
    CadInputQueue.SendKeyin "PRINT BOUNDARY FENCE"
    CadInputQueue.SendKeyin "PRINT MAXIMIZE"
    
    
    CadInputQueue.SendKeyin "PRINT EXECUTE " & filePath
    
    ' Show Levels
    For i = 1 To ActiveDesignFile.Levels.Count
        myView.ShowLevel ActiveDesignFile.Levels(i)
    Next i
    
    myView.Redraw
    
End Function

Function FitBoundary(mapBoundary As ComplexShapeElement, myView As View)
    Dim boundaryThickness As Point3d
    boundaryThickness = myView.Extents
    Dim ratioX As Double
    ratioX = 1597.4998 / boundaryThickness.X
    Dim ratioY As Double
    ratioY = 977.5122 / boundaryThickness.Y
    If ratioX > ratioY Then
        myView.ZoomAboutPoint mapBoundary.Centroid, ratioX
    Else
        myView.ZoomAboutPoint mapBoundary.Centroid, ratioY
    End If
End Function

Function GetRasterLevel() As Level
    Const levelName As String = "Raster Level"
    Dim rasterLevel As Level
    On Error Resume Next
    Set rasterLevel = ActiveDesignFile.Levels(levelName)
    If rasterLevel Is Nothing Then
        ' Create level
        Set rasterLevel = ActiveDesignFile.AddNewLevel(levelName)
        Levels.Rewrite
    End If
    
    Set GetRasterLevel = rasterLevel
End Function
    
Function t2()
    'RasterManager.Rasters.Item(1).GetBitmap(Point2dFromXY(1000, 1000), Point2dFromXY(100000, 100000), Point2dFromXY(1000, 1000)).ExportRaster "C:\Users\Jaden\Documents\Work\test.bmp", Nothing, Nothing, Nothing, Nothing
    CadInputQueue.SendKeyin "Plot Off"
End Function

Attribute VB_Name = "Road"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private road_name As String
Private bore_type As String
Private along_line As Boolean
Private line_length As Long

Property Let RoadName(name As String)
    road_name = name
End Property

Property Get RoadName() As String
    RoadName = road_name
End Property

Property Let BoreType(lineType As String)
    bore_type = lineType
End Property

Property Get BoreType() As String
    BoreType = bore_type
End Property

Property Get IsConventionalBore() As Boolean
    IsConventionalBore = InStr(UCase(bore_type), "BORE")
End Property

Property Let Along(lineType As Boolean)
    along_line = lineType
End Property

Property Get Along() As Boolean
    Along = along_line
End Property

Property Let Length(lineLength As Long)
    line_length = lineLength
End Property

Property Get Length() As Long
    Length = line_length
End Property

Function compareRoad(otherRoad As Road) As Integer
    If road_name <> otherRoad.RoadName Then
        ' US roads should be first
        If InStr(road_name, "US") = 0 And InStr(otherRoad.RoadName, "US") <> 0 Then
            compareRoad = -1
            Exit Function
        ElseIf InStr(road_name, "US") <> 0 And InStr(otherRoad.RoadName, "US") = 0 Then
            compareRoad = 1
            Exit Function
        End If
        compareRoad = StrComp(road_name, otherRoad.RoadName, vbTextCompare)
        Exit Function
    End If
    If IsConventionalBore() And Not otherRoad.IsConventionalBore Then
        compareRoad = -1
        Exit Function
    ElseIf Not IsConventionalBore() And otherRoad.IsConventionalBore Then
        compareRoad = 1
        Exit Function
    End If
    If bore_type <> otherRoad.BoreType Then
        compareRoad = StrComp(bore_type, otherRoad.BoreType, vbTextCompare)
    End If
    If along_line And Not otherRoad.Along Then
        compareRoad = -1
        Exit Function
    ElseIf Not along_line And otherRoad.Along Then
        compareRoad = 1
        Exit Function
    End If
    compareRoad = 0
End Function

Function ToString() As String
    Dim text As String
    text = UCase(Left(bore_type, 1)) & LCase(Right(bore_type, Len(bore_type) - 1)) & " "
    If along_line Then
        text = text & "along "
    Else
        text = text & "across "
    End If
    text = text & road_name & " a total of " & line_length & " feet of " & MapFormatForm.CabelType
    ToString = text
End Function
