Attribute VB_Name = "ActionPoint"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'This class describes points along the plow path
'The points can be any of the following:
'NONE         - Not defined
'SWITCH       - A switch point between boring and plowing (bore pit)
'INTERSECTION - A point that required boring because of some intersecting object
'MATCH        - A point at which the match line interescts

Private point_type As String
Private point_distance As Double
Private normal_forward As Boolean 'Whether the normal bore line is forward of this point
Private variant_type As Boolean

Property Get PointType() As String
    PointType = point_type
End Property

Property Get PointDistance() As Double
    PointDistance = point_distance
End Property

Property Let PointType(pType As String)
    point_type = pType
End Property

Property Let PointDistance(pDistance As Double)
    point_distance = pDistance
End Property

Property Get IsSwitch() As Boolean
    IsSwitch = point_type = "SWITCH"
End Property

Property Get VariantType() As Boolean
    VariantType = variant_type
End Property

Property Get NormalForward() As Boolean
    NormalForward = normal_forward
End Property

Property Let VariantType(newType As Boolean)
    variant_type = newType
End Property

Property Let NormalForward(newNormal As Boolean)
    normal_forward = newNormal
End Property

Private Sub Class_Initialize()
    point_type = "NONE"
    point_distance = 0
    normal_forward = True
    variant_type = False
End Sub

Attribute VB_Name = "Arrays"

Public Sub QuickSort(vArray() As Double, inLow As Long, inHi As Long)
  Dim pivot   As Double
  Dim tmpSwap As Double
  Dim tmpLow  As Long
  Dim tmpHi   As Long

  tmpLow = inLow
  tmpHi = inHi
  
  pivot = vArray((inLow + inHi) \ 2)

  While (tmpLow <= tmpHi)
     While (vArray(tmpLow) < pivot And tmpLow < inHi)
        tmpLow = tmpLow + 1
     Wend

     While (pivot < vArray(tmpHi) And tmpHi > inLow)
        tmpHi = tmpHi - 1
     Wend

     If (tmpLow <= tmpHi) Then
        tmpSwap = vArray(tmpLow)
        vArray(tmpLow) = vArray(tmpHi)
        vArray(tmpHi) = tmpSwap
        tmpLow = tmpLow + 1
        tmpHi = tmpHi - 1
     End If
  Wend

  If (inLow < tmpHi) Then QuickSort vArray, inLow, tmpHi
  If (tmpLow < inHi) Then QuickSort vArray, tmpLow, inHi
End Sub

Public Sub QuickActionSort(vArray() As ActionPoint, inLow As Long, inHi As Long)
  Dim pivot   As ActionPoint
  Dim tmpSwap As ActionPoint
  Dim tmpLow  As Long
  Dim tmpHi   As Long

  tmpLow = inLow
  tmpHi = inHi
  
  Set pivot = vArray((inLow + inHi) \ 2)

  While (tmpLow <= tmpHi)
     While (vArray(tmpLow).PointDistance < pivot.PointDistance And tmpLow < inHi)
        tmpLow = tmpLow + 1
     Wend

     While (pivot.PointDistance < vArray(tmpHi).PointDistance And tmpHi > inLow)
        tmpHi = tmpHi - 1
     Wend

     If (tmpLow <= tmpHi) Then
        Set tmpSwap = vArray(tmpLow)
        Set vArray(tmpLow) = vArray(tmpHi)
        Set vArray(tmpHi) = tmpSwap
        tmpLow = tmpLow + 1
        tmpHi = tmpHi - 1
     End If
  Wend

  If (inLow < tmpHi) Then QuickActionSort vArray, inLow, tmpHi
  If (tmpLow < inHi) Then QuickActionSort vArray, tmpLow, inHi
End Sub

Public Sub QuickIntersectionSort(vArray() As IntersectionPoint, inLow As Long, inHi As Long)
  Dim pivot   As IntersectionPoint
  Dim tmpSwap As IntersectionPoint
  Dim tmpLow  As Long
  Dim tmpHi   As Long

  tmpLow = inLow
  tmpHi = inHi
  
  Set pivot = vArray((inLow + inHi) \ 2)
  
  Dim lowPt As IntersectionPoint
  Dim highPt As IntersectionPoint

  While (tmpLow <= tmpHi)
     While (vArray(tmpLow).PointDistance < pivot.PointDistance And tmpLow < inHi)
        tmpLow = tmpLow + 1
     Wend

     While (pivot.PointDistance < vArray(tmpHi).PointDistance And tmpHi > inLow)
        tmpHi = tmpHi - 1
     Wend

     If (tmpLow <= tmpHi) Then
        Set tmpSwap = vArray(tmpLow)
        Set vArray(tmpLow) = vArray(tmpHi)
        Set vArray(tmpHi) = tmpSwap
        tmpLow = tmpLow + 1
        tmpHi = tmpHi - 1
     End If
  Wend

  If (inLow < tmpHi) Then QuickIntersectionSort vArray, inLow, tmpHi
  If (tmpLow < inHi) Then QuickIntersectionSort vArray, tmpLow, inHi
End Sub

Attribute VB_Name = "AutoBoreForm"
Attribute VB_Base = "0{C054036A-74FF-4592-A883-01C094AD88C1}{AD3727AF-7B53-4DA6-8C86-FE7633F6DBC1}"
Attribute VB_GlobalNameSpace = False
Attribute VB_Creatable = False
Attribute VB_PredeclaredId = True
Attribute VB_Exposed = False
Attribute VB_TemplateDerived = False
Attribute VB_Customizable = False
' Add this at the top of your module
Private Declare PtrSafe Function ShellExecute Lib "shell32.dll" Alias "ShellExecuteA" ( _
    ByVal hwnd As LongPtr, _
    ByVal lpOperation As String, _
    ByVal lpFile As String, _
    ByVal lpParameters As String, _
    ByVal lpDirectory As String, _
    ByVal nShowCmd As Long) As LongPtr
    
Private Sub Activate_Click()
    AutoBoreModule.AutoBore
End Sub

Private Sub ChangeBoreHandHole_Click()
    EditModule.ChangeBoreHandHole
End Sub

Private Sub CheckBox1_Click()

End Sub

Private Sub CommandButton1_Click()
    EditModule.AddPit
End Sub

Private Sub CommandButton10_Click()
    PolesModule.MovePoles
End Sub

Private Sub CommandButton11_Click()
    LevelsModule.DisableReferenceLevels
End Sub

Private Sub CommandButton2_Click()
    EditModule.RemovePit
End Sub

Private Sub CommandButton3_Click()
    MatchlineModule.CreateMatchlines
End Sub

Private Sub CommandButton4_Click()
    PolesModule.MovePoles
End Sub

Private Sub CommandButton5_Click()
    PropertyLineModule.DimensionProperty
End Sub

Private Sub CommandButton6_Click()
    RoadsModule.FormatSRNumbers
End Sub

Private Sub CommandButton7_Click()
    EditModule.ConvertOldAddressesLevel
End Sub

Private Sub CommandButton8_Click()
    EditModule.ConvertBoundaryShapes
End Sub

Private Sub CommandButton9_Click()
    RWModule.AddAllRWDimensions
End Sub


Private Sub Label40_Click()
    MsgBox "PinTech Corporation is not liable for any injuries or side effects caused by clicking ""Activate"" including, but not limited to, physical and psychological harm, pain and suffering, illness, disfigurement, temporary or permanent disability, and even death.", vbExclamation, "Disclaimer"
End Sub


Private Sub RelocateLabels_Click()
    LocationModule.moveSelectedDimensionText
End Sub



Private Sub UpdateLabel_Click()
    ShellExecute 0, "open", UpdateModule.downloadLink, vbNullString, vbNullString, 1
End Sub

Attribute VB_Name = "AutoBoreModule"
Sub Main()
    AutoBoreForm.Show vbModless
    UpdateModule.CheckUpdate
    If UpdateModule.updateString = "" Then
        'Hide components
        AutoBoreForm.UpdateLabel.Visible = False
    Else
        AutoBoreForm.UpdateLabel.Visible = True
        AutoBoreForm.UpdateLabel.Caption = UpdateModule.updateString
    End If
End Sub

'<===> AUTO BORE MAIN <===>
' ToDo:

'Activate switches to just dimensioning for dimensioning single road crossings
'Make Add Right of Way Labels program change dimension type like dimensionRWEOP
'Save settings to a file and load them when the program starts
'More flags (or fix these) for possible errors like RWEOP dimensions having decimals, or being too close to the R/W, or R/W dimension has a decimal, or bore line <6 to be dimensioned, or couldn't find space for things
'Make dimensionRWEOP use the RW point and bore line point to make the road dimension the same direction

'Road crossing changes
'If the intersection point is within 10 feet of the EOP, it needs to be pushed further back from the crossing

'Auto complex chain
'Search for unconnected lines of the same type at the endpoint
'If the lines intersect, end the lines at the intersection (trim)
'If the lines don't intersect, draw a new line to connect them
'perhaps a future use of this is to make the centerlines chained together, and when dimensioning an bore line crossing a road, the intersected centerline can be probed for road names

' MAIN FUNCTION
' This starts and ends the auto bore process
Function AutoBore()
    Debug.Print "Auto Bore Start"
    'Get starting element from selection
    If Not ActiveModelReference.AnyElementsSelected Then
        MsgBox "The macro requires a selection set"
        Exit Function
    End If
    Dim ee As ElementEnumerator
    Set ee = ActiveModelReference.GetSelectedElements 'Selected elements
    ee.Reset
    ee.MoveNext 'Move to the first element
    'Check if it is a line
    Dim mainLine As ComplexStringElement
    
    If ee.Current.IsComplexStringElement Then
        Set mainLine = ee.Current.AsComplexStringElement
        mainLine.Level = ActiveModelReference.Levels("Level 30")
    ElseIf ee.Current.IsLineElement Then
        ' convert to complex string
        Debug.Print "Converting element to chain"
        Dim currentLine As LineElement
        Set currentLine = ee.Current
        Dim elements(2) As ChainableElement
        Set elements(0) = currentLine
        Dim startPt As Point3d
        Dim midPt As Point3d
        Dim endPt As Point3d
        startPt = currentLine.endPoint
        Dim dir As Point3d
        dir = Point3dScale(Point3dNormalize(Point3dSubtract(currentLine.Vertex(currentLine.VerticesCount), currentLine.Vertex(currentLine.VerticesCount - 1))), 0.05)
        midPt = Point3dAdd(startPt, dir)
        endPt = Point3dAdd(midPt, dir)
        Set elements(1) = CreateArcElement1(currentLine, startPt, midPt, endPt)
        Set mainLine = CreateComplexStringElement1(elements)
        mainLine.Level = ActiveModelReference.Levels("Level 30")
        ActiveModelReference.RemoveElement currentLine
        ActiveModelReference.AddElement mainLine
        mainLine.Redraw
        mainLine.Rewrite
    Else
        MsgBox "The macro requires a line element or complex string element " & ee.Current.Type
        Exit Function
    End If
    
    Dim prevLevel As Level
    Dim prevLineStyle As LineStyle
    Dim prevLineWeight As Long
    Dim prevLineColor As Long
    Dim prevDimensionStyle As DimensionStyle
    With ActiveSettings
        Set prevLevel = .Level
        Set prevLineStyle = .LineStyle
        prevLineWeight = .LineWeight
        prevLineColor = .Color
        Set prevDimensionStyle = .DimensionStyle
    End With
    
    Dim msg As String ' A message to be sent in the messages area and the immediate window about bore information
    
    ' Collecting all the intersections to the bore line
    Dim intersections As New Collection
    Dim intersectionsIndex
    Dim intersectingCulverts As Collection
    Set intersectingCulverts = getIntersectingCulverts(mainLine)
    msg = intersectingCulverts.count & " Intersecting Culverts."
    
    Dim intersectingBridges As Collection
    Set intersectingBridges = getIntersectingBridges(mainLine)
    msg = msg & vbNewLine & intersectingBridges.count & " Intersecting Bridge Points = " & intersectingBridges.count / 2 & " Bridges."
    
    Dim drivewayIntersections As Collection
    Set drivewayIntersections = getDrivewayIntersections(mainLine)
    msg = msg & vbNewLine & drivewayIntersections.count / 2 & " Intersecting Driveways."
    
    
    Dim soilIntersections As Collection
    Set soilIntersections = getSoilIntersections(mainLine)
    msg = msg & vbNewLine & soilIntersections.count / 2 & " Intersecting Soil/Gravel Patches."
    
    Dim poleIntersections As Collection
    Set poleIntersections = getPoleIntersections(mainLine)
    msg = msg & vbNewLine & poleIntersections.count & " Nearby Poles."
    
    Dim guardrailIntersections As Collection
    Set guardrailIntersections = getGuardrailIntersections(mainLine)
    msg = msg & vbNewLine & guardrailIntersections.count & " Nearby Guardrails."
    
    Dim matchIntersections As Collection
    Set matchIntersections = getMatchIntersections(mainLine)
    msg = msg & vbNewLine & matchIntersections.count & " Intersecting Match Lines."
    
    Dim roadIntersections As Collection
    Set roadIntersections = getRoadIntersections(mainLine)
    msg = msg & vbNewLine & roadIntersections.count / 2 & " Road Crossings."
    
    Dim switches As IntersectionList
    Set switches = SmartAutoBore.CreateBoreSegments(ConvertToDistances(mainLine, intersectingCulverts), soilIntersections, poleIntersections, matchIntersections, roadIntersections, ConvertToDistances(mainLine, intersectingBridges), ConvertToDistances(mainLine, drivewayIntersections), guardrailIntersections, mainLine.length)
    
    switches.PrintPoints
    
    Dim roadNames As Collection
    Dim maxDistance As Double 'Maximum distance the text can be from the mainLine
    maxDistance = CDbl(AutoBoreForm.MaxRWDistance) / 2
    Set roadNames = AutoBoreModule.getRoadNames(mainLine, maxDistance)
    msg = msg & vbNewLine & roadNames.count & " Applicable Road Name Elements."
    
    Dim mainLineCopy As ComplexStringElement
    Set mainLineCopy = mainLine.Clone
    
    SmartAutoBore.BreakBoreLine mainLine, switches, roadNames
    
    DimensionEOPRW mainLineCopy, matchIntersections, roadIntersections
    
    'Undefine fence
    ActiveDesignFile.Fence.Undefine
    
    ' Calculate some info to send in a completion msg
    Dim plowLength As Double
    Dim boreLength As Double
    Dim borePits As Integer
    Dim handHoles As Integer
    plowLength = 0
    boreLength = 0
    borePits = 0
    handHoles = 0
    Dim intersection As IntersectionPoint
    Dim i As Long
    For i = 0 To switches.size - 1
        Set intersection = switches.At(i)
        If intersection.PointType = "BORE" Then
            boreLength = boreLength + intersection.PointDistance
        ElseIf intersection.PointType = "PLOW" Then
            plowLength = plowLength + intersection.PointDistance
        ElseIf intersection.PointType = "BOREPIT" Then
            borePits = borePits + 1
        ElseIf intersection.PointType = "HANDHOLE" Then
            handHoles = handHoles + 1
        End If
    Next i
    
    If AutoBoreForm.EnableMessages Then MessageCenter.AddMessage msg
    Debug.Print msg
    If AutoBoreForm.FeedbackMsg Then MsgBox "Scrubbed (unrounded): " & vbNewLine & Int(plowLength) & " ft PLOW" & vbNewLine & Int(boreLength) & " ft BORE" & vbNewLine & borePits & " bore pits" & vbNewLine & handHoles & " hand holes", vbInformation, "Missiles Deployed"
    
    ' Return active settings
    With ActiveSettings
        Set .Level = prevLevel
        Set .LineStyle = prevLineStyle
        .LineWeight = prevLineWeight
        .Color = prevLineColor
        Set .DimensionStyle = prevDimensionStyle
    End With
End Function

'*POST PROCESSING*
'Break the lines up at switch points and change attributes of lines between switch points with an intersection point in the middle
'Search within 5 feet of switch points for a R/W line
'Add bore pit element offset towards the R/W and rotated to be in line
'Continue 20' or so in the same direction to paste bore pit text
'Add match line intersection points to list
'If match line point is next to an intersection, add another sudo intersection on the other side
'Replace match lines with a switch point
'Iterate through list again
'For each 2 switch points
'Measure distance & record midpoint
'If the switch points contain an intersection, use directional bore along, otherwise plow
'Use template and replace distance with measured distance along
'Place element at midpoint
'add handhole at one side of bridges

Function BreakLine(mainLine As ComplexStringElement, point_list As PointList, roadNames As Collection, roadIntersections As Collection)
    Dim referenceLine As ComplexStringElement
    Set referenceLine = mainLine.Clone
    Dim i As Long
    Dim interestPoint As ActionPoint
    Dim lastInterestPoint As ActionPoint
    Dim point As Point3d
    Dim edge As Point3d
    Dim element1 As Element
    Dim element2 As Element
    Dim dimensioned As Double
    Dim dimensionedString As String
    Dim nearby As Collection
    Dim roadName As String
    Dim bore As Boolean
    Dim dimensionedElement As TextNodeElement
    'Check for hand hole near start
    Set nearby = Utils.NearbyElements(referenceLine.startPoint, 10)
    Dim addHandHole As Boolean
    Dim nearBorePit As ComplexShapeElement
    Dim direction As Vector3d
    Dim foundBoreLine As Boolean
    Dim breakDistance As Double
    foundBoreLine = False
    addHandHole = True
    dimensioned = 0
    'First check for another bore line
    For i = 1 To nearby.count
        Set element1 = nearby.item(i)
        If element1.IsComplexStringElement Then
        If element1.Level.name = "Level 30" Then
                If foundBoreLine Then
                    'New line element
                    addHandHole = False
                    Exit For
                Else
                    foundBoreLine = True
                End If
            End If
        ElseIf IsBorePit(element1) Then
                'Bore pit
                Set nearBorePit = element1.AsComplexShapeElement
                If dimensioned = 0 Then
                    dimensioned = (4.656 / 2)
                End If
        ElseIf element1.IsCellElement Then
            If element1.AsCellElement.name = "EXIST UTILITIES TELEPHONE HAND HOLE" Then
                'Hand hole
                addHandHole = False
                dimensioned = 5.725
                Exit For
            End If
        End If
    Next i
    If addHandHole Then
        'Should add a handhole
        If Not nearBorePit Is Nothing Then
            'There is a nearby bore pit to change
            'EditModule.BorePitToHandHole nearBorePit
        Else
            'Place new handhole
            point = referenceLine.startPoint
            edge = referenceLine.PointAtDistance(2.3)
            'Move points backwards to fit handhole w/o breaking the line
            direction = Vector3dScale(Vector3dNormalize(Vector3dSubtractPoint3dPoint3d(point, edge)), (5.725 / 2))
            point = Point3dAddPoint3dVector3d(point, direction)
            edge = Point3dAddPoint3dVector3d(edge, direction)
            PlaceHandHole point, edge
        End If
    End If
    For i = 0 To point_list.size - 1
        Set interestPoint = point_list.At(i)
        'Check if point is near other element
        
        If interestPoint.IsSwitch Or interestPoint.PointType = "MATCH" Then
            If interestPoint.PointDistance + 3 < referenceLine.length And interestPoint.PointDistance - 3 > 0 Then
                'Is a switch point or match point
                If i <> 0 Then 'First dimension may add a hand hole or bore pit dimension
                    dimensioned = 0
                End If
                Set element1 = Nothing
                Set element2 = Nothing
                'Convert distance into position
                point = referenceLine.PointAtDistance(interestPoint.PointDistance)
                'Break mainLine at point
                mainLine.PartialDelete element1, element2, point, point, point, 1
                'element1 and element2 are the new split parts
                'element1 = before line, element2 = after line
                'Remove previous line
                ActiveModelReference.RemoveElement mainLine
                If interestPoint.IsSwitch Then
                    'Place bore pit or hand hole
                    'find edge point that is 2.3 ft from point along mainLine
                    
                    If interestPoint.NormalForward Then
                        edge = referenceLine.PointAtDistance(interestPoint.PointDistance + 2.3)
                    Else
                        edge = referenceLine.PointAtDistance(interestPoint.PointDistance - 2.3)
                        'This edge will give problems when orienting elements, so we just need to mirror this to the other side of point
                        edge = Point3dAdd(point, Point3dSubtract(point, edge))
                    End If
                    If interestPoint.VariantType Then
                        PlaceHandHole point, edge
                        dimensioned = dimensioned + (5.725)
                        'Break lines
                        Dim e1 As Element
                        Dim e2 As Element
                        Dim breakPoint As Point3d
                        Dim breakPoint1 As Point3d
                        'Check if the angle between the breakpoints is less than 135 degrees
                        'The handhole may be a direction change
                        'Lengthen element1 if normal forward is true
                        breakPoint = referenceLine.PointAtDistance(interestPoint.PointDistance - (5.725 / 2)) 'Half a handhole back
                        breakPoint1 = referenceLine.PointAtDistance(interestPoint.PointDistance + (5.725 / 2)) 'Half a handhole forward
                        If Point3dAngleBetweenVectors(Point3dSubtract(breakPoint, point), Point3dSubtract(breakPoint1, point)) < 2.356 Then '135 degrees in radians
                            'Direction change handhole
                            If interestPoint.NormalForward Then
                                breakPoint = referenceLine.PointAtDistance(interestPoint.PointDistance - 1.7272) 'Not as far back
                            Else
                                breakPoint1 = referenceLine.PointAtDistance(interestPoint.PointDistance + 1.7272) 'Not as far forward
                            End If
                        End If
                        'element1
                        element1.PartialDelete e1, e2, breakPoint, breakPoint, breakPoint, 1
                        Set element1 = e1
                        'element2
                        If Not element2 Is Nothing Then
                            element2.PartialDelete e1, e2, breakPoint1, breakPoint1, breakPoint1, 1
                            Set element2 = e2
                        End If
                    Else
                        PlaceBorePit point, edge
                        dimensioned = dimensioned + (4.656 / 2)
                    End If
                End If
            
                'Redraw elements
                If Not element1 Is Nothing Then
                    ActiveModelReference.AddElement element1
                    element1.Redraw
                    dimensioned = dimensioned + element1.AsChainableElement.length
                Else
                    Debug.Print "Cant split element here"
                End If
                If Not element2 Is Nothing Then
                    ActiveModelReference.AddElement element2
                    element2.Redraw
                    Set mainLine = element2
                End If
                
                bore = False
                If i <> 0 And Not element1 Is Nothing Then
                    'Check if element1 should be bored
                    'Last point should be an intersection
                    If point_list.At(i - 1).PointType = "INTERSECTION" Then
                        'Bore
                        Set element1.LineStyle = element1.Level.ElementLineStyle
                        element1.Redraw msdDrawingModeNormal
                        element1.Rewrite
                        bore = True
                    End If
                End If
                'Check if last point has a bore pit
                If Not lastInterestPoint Is Nothing Then
                    'There is a match or switch point before this
                    If lastInterestPoint.IsSwitch Then
                        If lastInterestPoint.VariantType Then
                            'Handhole
                            dimensioned = dimensioned + 5.725
                        Else
                            'Bore Pit
                            dimensioned = dimensioned + (4.656 / 2)
                        End If
                    End If
                End If
                If Not element1 Is Nothing Then
                    'Dimension line
                    DimensionLine element1.AsChainableElement, dimensioned, interestPoint.PointDistance, roadNames, roadIntersections, bore
                End If
                
                Set lastInterestPoint = interestPoint
            End If
        End If
    Next i
    'Check if handholes should be added at the end points
    'No other line or handhole element should be nearby
    
    'Do other point (a little different)
    addHandHole = True
    Set nearBorePit = Nothing
    Set nearby = Utils.NearbyElements(referenceLine.endPoint, 10)
    foundBoreLine = False
    dimensioned = 0
    'First check for another bore line
    For i = 1 To nearby.count
        Set element1 = nearby.item(i)
        If element1.IsComplexStringElement Or element1.IsLineElement Then
            If element1.Level.name = "Level 30" Then
                If foundBoreLine Then
                    'New line element
                    addHandHole = False
                Else
                    foundBoreLine = True
                End If
            End If
        ElseIf IsBorePit(element1) Then
                'Bore pit
                Set nearBorePit = element1.AsComplexShapeElement
                If dimensioned = 0 Then
                    dimensioned = (4.656 / 2)
                End If
        ElseIf element1.IsCellElement Then
            If element1.AsCellElement.name = "EXIST UTILITIES TELEPHONE HAND HOLE" Then
                'Hand hole
                addHandHole = False
                dimensioned = 5.725
                Exit For
            End If
        End If
    Next i
    If addHandHole Then
        dimensioned = 5.725
        'Should add a handhole
        If Not nearBorePit Is Nothing Then
            'There is a nearby bore pit to change
            'EditModule.BorePitToHandHole (nearBorePit)
        Else
            'Place new handhole
            point = referenceLine.endPoint
            edge = referenceLine.PointAtDistance(referenceLine.length - 2.3)
            'This edge will give problems when orienting elements, so we just need to mirror this to the other side of point
            edge = Point3dAdd(point, Point3dSubtract(point, edge))
            'Move points forward to fit handhole w/o breaking the line
            direction = Vector3dScale(Vector3dNormalize(Vector3dSubtractPoint3dPoint3d(edge, point)), (5.725 / 2))
            point = Point3dAddPoint3dVector3d(point, direction)
            edge = Point3dAddPoint3dVector3d(edge, direction)
            PlaceHandHole point, edge
        End If
    End If
    'Dimension the rest of mainLine
    If Not mainLine Is Nothing Then
        If Not lastInterestPoint Is Nothing Then
            If lastInterestPoint.VariantType Then
                'Handhole
                dimensioned = dimensioned + 5.725
            Else
                'Bore Pit
                dimensioned = dimensioned + (4.656 / 2)
            End If
        End If
        dimensioned = dimensioned + mainLine.length
        'Get last point on line
        If point_list.size > 0 Then
            Set interestPoint = point_list.At(point_list.size - 1)
            bore = interestPoint.PointType = "INTERSECTION" 'Bore if it is an intersection
            If bore Then
                'Change color
                Set mainLine.LineStyle = mainLine.Level.ElementLineStyle
                mainLine.Redraw msdDrawingModeNormal
                mainLine.Rewrite
            End If
            'Dimension line
            DimensionLine mainLine.AsChainableElement, dimensioned, referenceLine.length, roadNames, roadIntersections, bore
        Else
            'No interest points
            DimensionLine mainLine.AsChainableElement, dimensioned, referenceLine.length, roadNames, roadIntersections, False
        End If
    End If
End Function

'Creates dimension elements to dimension the distance between the bore line and the R/W and EOP
'Only one dimension will be placed between each match line
'An open spot will be choosen if possible
Function DimensionEOPRW(mainLine As ComplexStringElement, matchIntersections As Collection, roadIntersections As Collection)
    Dim dimensionTemplate As dimensionElement
    Set dimensionTemplate = Utils.getDimensionTemplate()
    Dim rightOfWay As Point3d
    Dim road As Point3d
    Dim beforeDistance As Double
    Dim distance As Double
    Dim currPoint As Point3d
    Dim afterDistance As Double
    Dim distanceModifier As Double
    Dim closest As Collection
    Dim lookingForSpace As Boolean
    Dim nearby As Collection
    Dim searchPoint As Point3d
    Dim clearInside As Boolean
    Dim insideElement As Element
    'Change active level
    ActiveSettings.Level = ActiveDesignFile.Levels("Level 30")
    ActiveSettings.LineWeight = 0
    ActiveSettings.LineStyle = ActiveDesignFile.LineStyles("0")
    ActiveSettings.Color = 3
    'Iterate through match intersections
    For i = 1 To matchIntersections.count + 1
        'Get current and surrounding distances
        If i = 1 Then
            beforeDistance = 0 'Begining of the line
        Else
            beforeDistance = afterDistance 'Last match point
        End If
        If i = matchIntersections.count + 1 Then
            afterDistance = mainLine.length 'End of the line
        Else
            afterDistance = matchIntersections.item(i) 'Current match point
        End If
        
        distance = (afterDistance + beforeDistance) / 2 'Center point
        distanceModifier = 0
        lookingForSpace = True
        Dim iterations As Integer
        iterations = 0
        Do While lookingForSpace
            If distance + distanceModifier > mainLine.length Or distance + distanceModifier < 0 Then Exit Do
            currPoint = mainLine.PointAtDistance(distance + distanceModifier) 'Current point on the line that space is being looked for
            
            'Get nearby road and R/W
            Set closest = getClosestRWEOP(currPoint)
            If Not closest Is Nothing Then
                'Valid R/W and road objects
                rightOfWay = closest.item(1)
                road = closest.item(2)
                
                'Get nearby objects outside the R/W w/ a radius of 20 feet
                'Use search point that is 20.5 feet out (immediate R/W won't get hit by search)
                searchPoint = Point3dAdd(rightOfWay, Point3dScale(Point3dNormalize(Point3dSubtract(rightOfWay, currPoint)), 20.5))
                Set nearby = Utils.NearbyElements(searchPoint, 20)
                Dim allowedElements As Integer
                allowedElements = 0
                For j = 1 To nearby.count
                    Set insideElement = nearby.item(j)
                    If Not insideElement.Level Is Nothing Then
                        If insideElement.Level.name = "Exist Right of Way Line" Or insideElement.Level.name = "Level 30" Or insideElement.Level.name = "CATV Line UBO Text" Then
                            
                            If Not ((insideElement.IsTextElement Or insideElement.IsTextNodeElement) And insideElement.Level.name = "Level 30") Then
                                allowedElements = allowedElements + 1
                            End If
                        End If
                    End If
                Next j
                If nearby.count - allowedElements = 0 And Not IsInsidePath(distance + distanceModifier, roadIntersections) Then
                    'spot works
                    'Search inside for culverts
                    Set nearby = Utils.NearbyElements(road, 20)
                    clearInside = True
                    For j = 1 To nearby.count
                        Set insideElement = nearby.item(j)
                        If insideElement.IsCellElement Then
                            'This gets guardrails and poles
                            Dim eleEn As ElementEnumerator
                            Set eleEn = insideElement.AsComplexElement.GetSubElements()
                            While eleEn.MoveNext
                                If eleEn.Current.Color = 6 Or eleEn.Current.Color = 3 Then
                                    clearInside = False
                                    Exit For
                                End If
                                ' By Level Color
                                If eleEn.Current.Color = -1 And Not eleEn.Current.Level Is Nothing Then
                                    If eleEn.Current.Level.ElementColor = 6 Or eleEn.Current.Level.ElementColor = 3 Then
                                        clearInside = False
                                        Exit For
                                    End If
                                End If
                            Wend
                        ElseIf Not insideElement.Level Is Nothing Then
                            If insideElement.IsTextElement Or insideElement.IsTextNodeElement Then
                                If insideElement.Level.name <> "CATV Line UBO Text" Then
                                    'Text
                                    clearInside = False
                                    Exit For
                                End If
                            ElseIf insideElement.IsIntersectableElement Then
                                'This covers culverts & bridges & matchlines
                                
                                    If insideElement.Color = 6 Or insideElement.Color = 3 Then
                                        clearInside = False
                                        Exit For
                                    End If
                                    ' By Level Color
                                    If insideElement.Color = -1 And Not insideElement.Level Is Nothing Then
                                    If insideElement.Level.ElementColor = 6 Or insideElement.Level.ElementColor = 3 Then
                                        clearInside = False
                                        Exit For
                                    End If
                                End If
                             End If
                        End If
                    Next j
                    If clearInside Then
                        lookingForSpace = False
                        Exit Do
                    End If
                End If
            End If
            If lookingForSpace Then
                'Need to search more
                'Move 30 feet along the line
                If distanceModifier < 0 Then
                    distanceModifier = distanceModifier - 30
                Else
                    distanceModifier = distanceModifier + 30
                End If
                'Alternate sides
                distanceModifier = distanceModifier * -1
                'Verify point is within bounds
                If (distanceModifier + distance) < beforeDistance Or (distanceModifier + distance) > afterDistance Then
                    'Out of bounds
                    distanceModifier = 0
                    lookingForSpace = False 'Leave loop
                    Exit Do
                End If
            End If
            iterations = iterations + 1
            If iterations > 100 Then
                Debug.Print "Over 100 iterations"
                distanceModifier = 0
                Exit Do
            End If
        Loop
        
        'Spot selected -> distance + distanceModifier
        'Create dimension element
        Dim dimensionElement As dimensionElement
        Dim myView As View
        Set myView = CommandState.LastView
        If distance + distanceModifier - 5 < 0 Or distance + distanceModifier + 5 > mainLine.length Then
            distanceModifier = 0
        End If
        'Dimension to EOP
        currPoint = mainLine.PointAtDistance(distance + distanceModifier - 5)
        Set closest = getClosestRWEOP(currPoint)
        If closest Is Nothing Then Exit Function
        road = closest.item(2)
        Set ActiveSettings.DimensionStyle = dimensionTemplate.DimensionStyle
        Set dimensionElement = CreateDimensionElement1(dimensionTemplate, Utils.getRotationMatrix(Vector3dSubtractPoint3dPoint3d(road, currPoint), Vector3dFromXY(1, 0)), msdDimTypeCustomLinear, myView)
        Dim dimStyle As DimensionStyle
        Set dimStyle = dimensionTemplate.DimensionStyle
        dimensionElement.DimensionStyle = dimStyle
        'Add new points
        dimensionElement.AddReferencePoint ActiveModelReference, currPoint
        dimensionElement.AddReferencePoint ActiveModelReference, road
        dimensionElement.Color = 3
        dimensionElement.LineWeight = 0
        dimensionElement.Level = dimensionTemplate.Level
        
        'Add element
        ActiveModelReference.AddElement dimensionElement
        dimensionElement.Rewrite
        dimensionElement.Redraw
        
        
        'Dimension to R/W
        currPoint = mainLine.PointAtDistance(distance + distanceModifier + 5)
        Set closest = getClosestRWEOP(currPoint)
        rightOfWay = closest.item(1)
        Set dimensionElement = CreateDimensionElement1(dimensionTemplate, Utils.getRotationMatrix(Vector3dSubtractPoint3dPoint3d(rightOfWay, currPoint), Vector3dFromXY(-1, 0)), msdDimTypeCustomLinear, myView)
        'Add new points
        dimensionElement.AddReferencePoint ActiveModelReference, rightOfWay
        dimensionElement.AddReferencePoint ActiveModelReference, currPoint
        dimensionElement.Color = 3
        dimensionElement.LineWeight = 0
        dimensionElement.Level = dimensionTemplate.Level
        'Add element
        ActiveModelReference.AddElement dimensionElement
        dimensionElement.Rewrite
        dimensionElement.Redraw
    Next i
End Function

Function IsInsidePath(distance As Double, intersections As Collection) As Boolean
    For i = 1 To intersections.count - 1
        If i Mod 2 = 1 And distance > intersections.item(i) And distance < intersections.item(i + 1) Then
            IsInsidePath = True
            Exit Function
        End If
    Next i
    IsInsidePath = False
End Function

Function DimensionLine(element1 As ChainableElement, dimensioned As Double, endPoint As Double, roadNames As Collection, roadIntersections As Collection, bore As Boolean)
    Dim edge As Point3d
    Dim dimensionedString As String
    Dim roadName As String
    Dim dimensionedElement As TextNodeElement
    If dimensioned > 6 Then
        dimensionedString = CStr(Int((dimensioned + 5) / 5) * 5)
        edge = element1.PointAtDistance(element1.length / 2)
        roadName = GetNearestRoad(endPoint - (element1.length / 2), roadNames)
        If bore Then
            'Check if crossing a road
            Dim startPoint As Double
            Dim along As Boolean
            along = True
            startPoint = endPoint - element1.length
            Dim center As Double
            For i = 1 To roadIntersections.count Step 2
                center = (roadIntersections.item(i) + roadIntersections.item(i + 1)) / 2
                If center > startPoint And center < endPoint Then
                    'Road intersection between start and end
                    along = False
                    Exit For
                End If
            Next i
            If along Then
                Set dimensionedElement = Utils.CreateBoreDimension(edge, dimensionedString, roadName, 1)
            Else
                Set dimensionedElement = Utils.CreateBoreDimension(edge, dimensionedString, roadName, 2)
            End If
        Else
            Set dimensionedElement = Utils.CreateBoreDimension(edge, dimensionedString, roadName, 0)
        End If
        ActiveModelReference.AddElement dimensionedElement
        dimensionedElement.Redraw
    End If
End Function

'Get road names on design
'Returns an SR or NC if it contains one
'Only works if there is a double space seperating the name
'Returns a collection of ActionPoint objects
Function getRoadNames(mainLine As Element, maxDistance As Double) As Collection
    Dim roadNames As New Collection
    Dim roadName As String
    Dim oElement As Element
    Dim intersectPoint As Point3d
    'Create Scan for EOP text
    Dim oScanCriteria As ElementScanCriteria
    Set oScanCriteria = New ElementScanCriteria
    oScanCriteria.ExcludeAllLevels
    oScanCriteria.IncludeLevel ActiveModelReference.Levels("Exist Roads EOP Text")
    oScanCriteria.ExcludeAllTypes
    oScanCriteria.IncludeType msdElementTypeText
    oScanCriteria.IncludeType msdElementTypeTextNode
    Dim oScanEnumerator As ElementEnumerator
    Set oScanEnumerator = ActiveModelReference.Scan(oScanCriteria)
    'Iterate through scan
    Dim originpt As Point3d
    Dim text As String
    While oScanEnumerator.MoveNext
        Set oElement = oScanEnumerator.Current
        If oElement.IsTextNodeElement Then
            originpt = oElement.AsTextNodeElement.origin
            text = oElement.AsTextNodeElement.TextLine(1)
        Else
            originpt = oElement.AsTextElement.origin
            text = oElement.AsTextElement.text
        End If
        
        intersectPoint = mainLine.AsIntersectableElement.ProjectPointOnPerpendicular2(originpt, Matrix3dIdentity)
        'Check distance
        If Point3dDistance(intersectPoint, originpt) < maxDistance And InStr(text, " ") <> 0 Then
            roadName = Split(text, "  ")(0)
            roadNames.Add Utils.CreateActionPoint(roadName, mainLine.AsChainableElement.DistanceAtPoint(originpt))
        End If
    Wend
    Set getRoadNames = roadNames
End Function

Function GetNearestRoad(distance As Double, roadNames As Collection) As String
    If roadNames.count = 0 Then
        GetNearestRoad = "???"
        Exit Function
    End If
    Dim closestPoint As ActionPoint
    Set closestPoint = roadNames.item(1)
    Dim currPoint As ActionPoint
    For i = 2 To roadNames.count
        Set currPoint = roadNames.item(i)
        If Abs(distance - currPoint.PointDistance) < Abs(distance - closestPoint.PointDistance) Then
            'Closer
            Set closestPoint = currPoint
        End If
    Next i
    If Not closestPoint Is Nothing Then
        GetNearestRoad = closestPoint.PointType
    Else
        GetNearestRoad = "???"
    End If
End Function

Function getClosestRWEOPForRoad(point As Point3d, edge As Point3d) As Collection
    Dim maxRoadDistance As Double
    maxRoadDistance = CDbl(AutoBoreForm.MaxRWDistance)
    Dim forward As Point3d
    forward = Point3dSubtract(edge, point)
    forward = Point3dScale(Point3dRotateXY(forward, 1.5707), maxRoadDistance)
    Dim centerRay As LineElement
    Set centerRay = CreateLineElement2(Nothing, Point3dSubtract(point, forward), Point3dAdd(point, forward))
    
    Dim closest As New Collection
    Dim nearby As Collection
    Set nearby = Utils.NearbyElements(point, maxRoadDistance)
    Dim oElement As Element
    Dim road As Point3d
    Dim roadPresent As Boolean
    roadPresent = False
    Dim rightOfWay As Point3d
    Dim rightOfWayPresent As Boolean
    rightOfWayPresent = False
    Dim interestPoint As Point3d
    Dim hardRoad As Boolean
    hardRoad = False
    'Get closest R/W and road element
    For i = 1 To nearby.count
        Set oElement = nearby.item(i)
        If oElement.IsIntersectableElement And oElement.IsChainableElement Then
            ' Check if the element intersects the ray
            If UBound(centerRay.GetIntersectionPoints(oElement, Matrix3dIdentity)) <> -1 Then
                interestPoint = oElement.AsIntersectableElement.ProjectPointOnPerpendicular2(point, Matrix3dIdentity)
                If oElement.Level.name = "Exist Roads EOP" Then
                    'Road
                    If roadPresent Then
                        'Already have a road - check closer one
                        If Point3dDistance(interestPoint, point) < Point3dDistance(road, point) Or Not hardRoad Then
                            'Replace road
                            road = interestPoint
                            hardRoad = True
                        End If
                    Else
                        'Road is null
                        road = interestPoint
                        roadPresent = True
                        hardRoad = True
                    End If
                ElseIf oElement.Level.name = "Exist Roads Soil" And Not hardRoad Then
                    'Gravel Road
                    If roadPresent Then
                        'Already have a road - check closer one
                        If Point3dDistance(interestPoint, point) < Point3dDistance(road, point) Then
                            'Replace road
                            road = interestPoint
                        End If
                    Else
                        'Road is null
                        road = interestPoint
                        roadPresent = True
                    End If
                ElseIf oElement.Level.name = "Exist Right of Way Line" Then
                    'R/W
                    If rightOfWayPresent Then
                        'Already have a R/W - check closer one
                        If Point3dDistance(interestPoint, point) < Point3dDistance(rightOfWay, point) Then
                            'Replace R/W
                            rightOfWay = interestPoint
                        End If
                    Else
                        'R/W is null
                        rightOfWay = interestPoint
                        rightOfWayPresent = True
                    End If
                End If
            End If
        End If
    Next i
    'Check for R/W
    If Not rightOfWayPresent Then
        Debug.Print "No R/W nearby"
        Debug.Print point.x & " " & point.y
        Set getClosestRWEOPForRoad = Nothing
        Exit Function
    End If
    
    If Not roadPresent Then
        Debug.Print "No Road nearby"
        road = point
    End If
    
    closest.Add rightOfWay
    closest.Add road
    Set getClosestRWEOPForRoad = closest
End Function

Function getClosestRWEOP(point As Point3d) As Collection
    Dim closest As New Collection
    Dim maxRoadDistance As Double
    maxRoadDistance = CDbl(AutoBoreForm.MaxRWDistance)
    Dim nearby As Collection
    Set nearby = Utils.NearbyElements(point, maxRoadDistance)
    Dim oElement As Element
    Dim road As Point3d
    Dim roadPresent As Boolean
    roadPresent = False
    Dim rightOfWay As Point3d
    Dim rightOfWayPresent As Boolean
    rightOfWayPresent = False
    Dim interestPoint As Point3d
    Dim hardRoad As Boolean
    hardRoad = False
    'Get closest R/W and road element
    For i = 1 To nearby.count
        Set oElement = nearby.item(i)
        If oElement.IsIntersectableElement And oElement.IsChainableElement Then
            interestPoint = oElement.AsIntersectableElement.ProjectPointOnPerpendicular2(point, Matrix3dIdentity)
            If oElement.Level.name = "Exist Right of Way Line" Then
                'R/W
                If rightOfWayPresent Then
                    'Already have a R/W - check closer one
                    If Point3dDistance(interestPoint, point) < Point3dDistance(rightOfWay, point) Then
                        'Replace R/W
                        rightOfWay = interestPoint
                    End If
                Else
                    'R/W is null
                    rightOfWay = interestPoint
                    rightOfWayPresent = True
                End If
            End If
        End If
    Next i
    'Check for R/W
    If Not rightOfWayPresent Then
        Debug.Print "No R/W nearby"
        Debug.Print point.x & " " & point.y
        Set getClosestRWEOP = Nothing
        Exit Function
    End If
    
    'Construct vector from R/W to road
    Dim toRoad As Point3d
    toRoad = Point3dScale(Point3dNormalize(Point3dSubtract(point, rightOfWay)), maxRoadDistance)
    Dim lineRay As LineElement
    Set lineRay = CreateLineElement2(Nothing, point, Point3dAdd(point, toRoad))
    Dim intersectionPoints() As Point3d
    ' Find intersecting road elements
    For i = 1 To nearby.count
        Set oElement = nearby.item(i)
        If oElement.IsIntersectableElement And oElement.IsChainableElement Then
            intersectionPoints = lineRay.GetIntersectionPoints(oElement, Matrix3dIdentity)
            If UBound(intersectionPoints) <> -1 Then
                For j = LBound(intersectionPoints) To UBound(intersectionPoints)
                    interestPoint = intersectionPoints(j) 'oElement.AsIntersectableElement.ProjectPointOnPerpendicular2(point, Matrix3dIdentity)
                    If oElement.Level.name = "Exist Roads EOP" Then
                        'Road
                        If roadPresent Then
                            'Already have a road - check closer one
                            If Point3dDistance(interestPoint, point) < Point3dDistance(road, point) Or Not hardRoad Then
                                'Replace road
                                road = interestPoint
                                hardRoad = True
                            End If
                        Else
                            'Road is null
                            road = interestPoint
                            roadPresent = True
                            hardRoad = True
                        End If
                    ElseIf oElement.Level.name = "Exist Roads Soil" And Not hardRoad Then
                        'Gravel Road
                        If roadPresent Then
                            'Already have a road - check closer one
                            If Point3dDistance(interestPoint, point) < Point3dDistance(road, point) Then
                                'Replace road
                                road = interestPoint
                            End If
                        Else
                            'Road is null
                            road = interestPoint
                            roadPresent = True
                        End If
                    End If
                Next j
            End If
        End If
    Next i
    
    If Not roadPresent Then
        Debug.Print "No Road nearby"
        road = point
    End If
    
    closest.Add rightOfWay
    closest.Add road
    Set getClosestRWEOP = closest
End Function

Function PlaceBorePit(point As Point3d, edge As Point3d)
    Dim rightOfWay As Point3d
    Dim road As Point3d
    Dim closest As Collection
    Set closest = getClosestRWEOPForRoad(point, edge)
    If closest Is Nothing Then
        'R/W could not be found
        'MessageCenter.AddMessage "Bore Pit Placement Error", "No R/W near bore pit", msdMessageCenterPriorityError, True
        Exit Function
    End If
    rightOfWay = closest.item(1)
    road = closest.item(2)
    
    'Place pit
    Dim bore As Element
    Set bore = Utils.CreateBorePit(rightOfWay, point, edge)
    If Not bore Is Nothing Then
        ActiveModelReference.AddElement bore
        bore.Redraw
    End If
    
    'Get text Origin
    Dim outwardsDir As Vector3d
    outwardsDir = Vector3dScale(Vector3dSubtractPoint3dPoint3d(rightOfWay, point), 8)
    Dim textOrigin As Point3d
    textOrigin = Point3dAddPoint3dVector3d(rightOfWay, outwardsDir)
    'Place text
    Set boreText = Utils.CreateBoreText(textOrigin, CStr(Int(Point3dDistance(point, road) + 0.5)))
    If Not boreText Is Nothing Then
        boreText.Color = 87
        ActiveModelReference.AddElement boreText
        boreText.Redraw
    End If
End Function

Function PlaceHandHole(point As Point3d, edge As Point3d) As Element
    Dim rightOfWay As Point3d
    Dim road As Point3d
    Dim closest As Collection
    Set closest = getClosestRWEOPForRoad(point, edge)
    If closest Is Nothing Then
        'R/W could not be found
        'MessageCenter.AddMessage "Bore Pit Placement Error", "No R/W near bore pit", msdMessageCenterPriorityError, True
        Exit Function
    End If
    rightOfWay = closest.item(1)
    road = closest.item(2)
    
    'Place pit
    Dim bore As Element
    Set bore = Utils.CreateHandHole(rightOfWay, point, edge)
    If Not bore Is Nothing Then
        ActiveModelReference.AddElement bore
        bore.Redraw
    End If
    
    'Get text Origin
    Dim outwardsDir As Vector3d
    outwardsDir = Vector3dScale(Vector3dSubtractPoint3dPoint3d(rightOfWay, point), 8)
    Dim textOrigin As Point3d
    textOrigin = Point3dAddPoint3dVector3d(rightOfWay, outwardsDir)
    'Place text
    Dim boreText As Element
    Set boreText = Utils.CreateHandHoleText(textOrigin, CStr(Int(Point3dDistance(point, road) + 0.5)))
    If Not boreText Is Nothing Then
        boreText.Color = 87
        ActiveModelReference.AddElement boreText
        boreText.Redraw
    End If
    
    Set PlaceHandHole = bore
End Function


'Create a list of distances along the mainLine that bore pits will go to switch between plow and bore
'Returns a collection of doubles
Function CreateSwitchList(intersectionDistances As Collection, soilIntersections As Collection, poleIntersections As Collection, matchIntersections As Collection, roadIntersections As Collection, bridgeIntersections As Collection, drivewayIntersections As Collection) As PointList
    'The maximum distance that intersections can be away from eachother and continue to bore line between
    Dim maxIntersectionDistanceConnection As Double
    maxIntersectionDistanceConnection = CDbl(AutoBoreForm.MaxBoreConnectionDistance)
    Dim MinSoilExtend As Double
    MinSoilExtend = 100 'CDbl(AutoBoreForm.MinSoilExtend)
    Dim MaxSoilExtend As Double
    MaxSoilExtend = CDbl(AutoBoreForm.MaxSoilExtend)
    Dim maxPoleExtend As Double
    maxPoleExtend = CDbl(AutoBoreForm.maxPoleSnap)
    Dim point_list As New PointList
    Dim distance As Double
    Dim distance1 As Double
    Dim distanceBefore As Double
    Dim distanceAfter As Double
    distanceAfter = intersectionDistances.item(1)
    Dim isDriveway As Boolean
    Dim i As Long
    Dim j As Long
    'Add switch points
    'Not looking at the last intersection because it is the end point of the line
    'distanceBefore < distance < distanceAfter
    For i = 1 To intersectionDistances.count - 1
        'Intersection distance
        If i > 1 Then
            distanceBefore = distance
        Else
            distanceBefore = 0
        End If
        distance = distanceAfter
        distanceAfter = intersectionDistances.item(i + 1)
        'Check if it is a driveway intersection
        isDriveway = False
        For j = 1 To drivewayIntersections.count
            distance1 = drivewayIntersections.item(j)
            If distance1 = distance Then
                isDriveway = True
                Exit For
            End If
            'Past distance
            If distance1 > distance Then
                Exit For
            End If
        Next j
        'Check the distance to last intersection
        If distance - distanceBefore > maxIntersectionDistanceConnection Then
            'Intersection points far enough apart
            If isDriveway Then
                distance1 = distance - 15
            Else
                distance1 = distance - 75
            End If
            point_list.Add Utils.CreateActionPoint("SWITCH", distance1)
        End If
        'Add intersection point to list
        point_list.Add Utils.CreateActionPoint("INTERSECTION", distance)
        'Check the distance to next intersection
        If distanceAfter - distance > maxIntersectionDistanceConnection Then
            'Intersection points far enough apart
            If isDriveway Then
                distance1 = distance + 15
            Else
                distance1 = distance + 75
            End If
            point_list.Add Utils.CreateActionPoint("SWITCH", distance1)
        End If
    Next i

    'Iterate through list again and remove any extra intersection points
    'Only need one intersection point between switch points to denote that it is a bore area
    Dim interestPoint1 As ActionPoint
    Dim interestPoint2 As ActionPoint
    Dim removeIndicies As New Collection
    'Grab index of points to be removed
    For i = 0 To point_list.size - 2
        Set interestPoint1 = point_list.At(i)
        Set interestPoint2 = point_list.At(i + 1)
        If Not interestPoint1.IsSwitch And Not interestPoint2.IsSwitch Then
            removeIndicies.Add item:=i
        End If
    Next i
    'Remove those indicies
    For i = 1 To removeIndicies.count
        point_list.Remove removeIndicies.item(i) - (i - 1)
    Next i

    'The list should be in a format of: switch, intersection, switch, switch, intersection, switch, ...
    'Look for places to extend the switch points a bit
    'First soil, then snap to nearby poles not inside soil
    
    'Iterate through point list
    'When between 2 switch points
    'Get distance range
    'check for all soil within distance range (prob an efficient way to do this with only one interation of soil list)
    'For each switch: If any of the soil distance is less than 100 feet from switch, place a temporary new switch object 30 feet from the soil
    'If a temp switch was created and there is another soil within 100 ft, keep increasing distance with a max of 600 ft
    'Make variables for min and max
    'If max is reached, place in center of next open space > 40ft from original switch distance
    'Check for out of order temp switches - There is another temp switch before the switch they reference
    'Combine overlapping temp switches by removing referenced switches
    
    
    Dim soilInbetween As Collection
    Dim adjustedPoints As New Collection
    Dim adjustedPoint1 As ReferencedActionPoint
    Dim adjustedPoint2 As ReferencedActionPoint
    'Check for start case
    If point_list.size > 0 Then
    Set interestPoint1 = point_list.At(0)
        If interestPoint1.IsSwitch Then
            'Possibly extend start
            Set soilInbetween = getSoilInbetween(soilIntersections, 0, interestPoint1.PointDistance)
            If soilInbetween.count > 0 Then
                'Adjust point
                'maxSoilExtend is changed so it doesn't go off the line
                adjustedPoints.Add Utils.CreateReferencedActionPoint(getAdjustedSwitchPoint(interestPoint1.PointDistance, soilInbetween, MinSoilExtend, Min(MaxSoilExtend, interestPoint1.PointDistance), False), 0)
            End If
        End If
    End If
    For i = 0 To point_list.size - 2
        Set interestPoint1 = point_list.At(i)
        Set interestPoint2 = point_list.At(i + 1)
        If interestPoint1.IsSwitch And interestPoint2.IsSwitch Then
            'Both are switches - Check for soil inbetween
            Set soilInbetween = getSoilInbetween(soilIntersections, interestPoint1.PointDistance, interestPoint2.PointDistance)
            If soilInbetween.count > 0 Then
                'Adjust values
                adjustedPoints.Add Utils.CreateReferencedActionPoint(getAdjustedSwitchPoint(interestPoint1.PointDistance, soilInbetween, MinSoilExtend, MaxSoilExtend, True), i)
                adjustedPoints.Add Utils.CreateReferencedActionPoint(getAdjustedSwitchPoint(interestPoint2.PointDistance, soilInbetween, MinSoilExtend, MaxSoilExtend, False), i + 1)
            End If
        End If
    Next i
    If point_list.size > 0 Then
        'Check for end case
        Set interestPoint1 = point_list.At(point_list.size - 1)
        If interestPoint1.IsSwitch Then
            'Possibly extend end
            'mainLine end distance
            distance = intersectionDistances.item(intersectionDistances.count)
            Set soilInbetween = getSoilInbetween(soilIntersections, interestPoint1.PointDistance, distance)
            If soilInbetween.count > 0 Then
                'Adjust point
                'maxSoilExtend is changed so it doesn't go off the line
                adjustedPoints.Add item:=Utils.CreateReferencedActionPoint(getAdjustedSwitchPoint(interestPoint1.PointDistance, soilInbetween, MinSoilExtend, Min(MaxSoilExtend, distance - interestPoint1.PointDistance), True), point_list.size - 1)
            End If
        End If
    End If
    'Check for out of order temp switches - There is another temp switch before the switch they reference
    'Combine overlapping temp switches by removing referenced switches
    Set removeIndicies = Nothing
    For i = 1 To adjustedPoints.count - 1
        Set adjustedPoint1 = adjustedPoints.item(i)
        Set adjustedPoint2 = adjustedPoints.item(i + 1)
        'Check if next adjusted point is between the first adjusted point and its referenced point
        distance = point_list.At(adjustedPoint1.PointReference).PointDistance
        If adjustedPoint2.PointDistance > Min(adjustedPoint1.PointDistance, distance) And adjustedPoint2.PointDistance < Max(adjustedPoint1.PointDistance, distance) Then
            'Remove this switch and the next one
            removeIndicies.Add i
            removeIndicies.Add i + 1
        End If
    Next i
    'Update point_list with adjusted points
    For i = 1 To adjustedPoints.count
        Set adjustedPoint1 = adjustedPoints.item(i)
        'Debug.Print "Adjusting For Soil: " & point_list.At(adjustedPoint1.PointReference).PointDistance & " to " & adjustedPoint1.PointDistance
        point_list.SetPointDistance adjustedPoint1.PointReference, adjustedPoint1.PointDistance
    Next i
    'Remove items from removeIndicies
    Dim removeIndex As Long
    For i = 1 To removeIndicies.count
        removeIndex = removeIndicies.item(i) - (i - 1)
        Set adjustedPoint1 = adjustedPoints.item(removeIndex)
        adjustedPoints.Remove removeIndex 'Remove adjusted switch
        point_list.Remove adjustedPoint1.PointReference - (i - 1) 'Remove original switch
    Next i
    'adjustedPoints will no longer hold an accurate reference
    
    'Remove pole points in soil
    Dim soilIndex As Long
    soilIndex = 1
    Set removeIndicies = Nothing
    For i = 1 To poleIntersections.count
        'Get pole pos
        distance = poleIntersections.item(i)
        For j = 1 To soilIntersections.count - 1 Step 2 '2 step because each soil has 2 intersections
            distanceBefore = soilIntersections.item(j)
            distanceAfter = soilIntersections.item(j + 1)
            If distance > distanceBefore Then
                If distance < distanceAfter Then
                    'In soil patch
                    removeIndicies.Add i
                    Exit For
                End If
            End If
        Next j
    Next i
    'Remove items
    For i = 1 To removeIndicies.count
        removeIndex = removeIndicies.item(i) - (i - 1)
        poleIntersections.Remove (removeIndex)
    Next i
    'connect to nearby pole
    'check to still be 75' from intersectionDistances
    Set adjustedPoints = Nothing
    point_list.SortList
    For i = 0 To point_list.size - 1
        'Check if a switch point
        Set interestPoint1 = point_list.At(i)
        If interestPoint1.IsSwitch Then
            'Check for a nearby pole
            For j = 1 To poleIntersections.count
                distance = poleIntersections.item(j)
                'Check if within maxPoleExtend from interestPoint (below)
                If distance + maxPoleExtend >= interestPoint1.PointDistance Then
                    'Check if too far (above)
                    If distance - maxPoleExtend > interestPoint1.PointDistance Then
                        'Too far away
                        Exit For
                    End If
                    'Close enough
                    'Check if distance isn't too close to an intersection
                    'Before Point
                    If i = 0 Then
                        'Point at start of line, no intersection to worry about
                        distanceBefore = -75
                    Else
                        'Get prev interest point
                        distanceBefore = getNearbyIntersectingPoint(intersectionDistances, interestPoint1.PointDistance, False)
                    End If
                    'After Point
                    If i = point_list.size - 1 Then
                        'Point at end of line, no intersection to worry about
                        distanceAfter = intersectionDistances.item(intersectionDistances.count) + 75 '75 ft beyond end
                    Else
                        'Get next interest point
                        distanceAfter = getNearbyIntersectingPoint(intersectionDistances, interestPoint1.PointDistance, True)
                    End If
                    'Distance before and after are set to surrounding interesctions or the start/end of line
                    'Check if distance is at least 75 ft away from points
                    Debug.Print i & "-" & j & " B: " & distanceBefore & " C: " & distance & " A: " & distanceAfter
                    If distanceAfter - distance > 75 And distance - distanceBefore > 75 Then
                        'Save to update point index
                        adjustedPoints.Add Utils.CreateReferencedActionPoint(distance, i)
                    End If
                End If
            Next j
        End If
    Next i
    'Check for adjusted points with the same reference point
    'They should be next to eachother
    'Points will be changed to whichever is closest to the original
    For i = 1 To adjustedPoints.count - 1
        Set adjustedPoint1 = adjustedPoints.item(i)
        Set adjustedPoint2 = adjustedPoints.item(i + 1)
        If adjustedPoint1.PointReference = adjustedPoint2.PointReference Then
            'Same reference
            'Set to minimim distance to their reference
            Set interestPoint1 = point_list.At(adjustedPoint1.PointReference)
            If Abs(adjustedPoint1.PointDistance - interestPoint1.PointDistance) > Abs(adjustedPoint2.PointDistance - interestPoint1.PointDistance) Then
                'adjustedPoint2 is closer
                adjustedPoint1.PointDistance = adjustedPoint2.PointDistance
            Else
                'adjustedPoint1 is closer
                adjustedPoint2.PointDistance = adjustedPoint1.PointDistance
            End If
        End If
    Next i
    'Update point_list with adjusted points
    For i = 1 To adjustedPoints.count
        Set adjustedPoint1 = adjustedPoints.item(i)
        'Debug.Print "Adjusting For Pole: " & point_list.At(adjustedPoint1.PointReference).PointDistance & " to " & adjustedPoint1.PointDistance
        point_list.SetPointDistance adjustedPoint1.PointReference, adjustedPoint1.PointDistance
    Next i
    
    point_list.SortList
    
    'Remove any double intersection points or switch points close to eachother
    Set removeIndicies = Nothing
    Dim minFitDistance As Double
    minFitDistance = CDbl(AutoBoreForm.MinBoreFitSize)
    'Grab index of points to be removed
    For i = 0 To point_list.size - 2
        Set interestPoint1 = point_list.At(i)
        Set interestPoint2 = point_list.At(i + 1)
        If Not interestPoint1.IsSwitch And Not interestPoint2.IsSwitch Then
            removeIndicies.Add item:=i
        ElseIf interestPoint1.IsSwitch And interestPoint2.IsSwitch Then
            If Abs(interestPoint2.PointDistance - interestPoint1.PointDistance) < minFitDistance Then
                removeIndicies.Add item:=i
            End If
        End If
    Next i
    'Remove those indicies
    For i = 1 To removeIndicies.count
        point_list.Remove removeIndicies.item(i) - (i - 1)
    Next i
    
    'Add road intersections
    Dim terminateSurrounding As Boolean 'Whether surrounding intersections should be terminated at this road crossing
    Dim includesIntersection As Boolean
    Dim aPoint1 As ActionPoint
    Dim aPointBefore As ActionPoint
    Dim aPointAfter As ActionPoint
    Dim variantIntersectPoint As ActionPoint
    For i = 1 To roadIntersections.count - 1 Step 2
        terminateSurrounding = False
        distanceBefore = roadIntersections.item(i)
        distanceAfter = roadIntersections.item(i + 1)
        'Create switch points
        Set interestPoint1 = Utils.CreateActionPoint("SWITCH", distanceBefore)
        Set interestPoint2 = Utils.CreateActionPoint("SWITCH", distanceAfter)
        
        'Check if there is any switches inside - this controls if terminateSurrounding should be true
        Set aPointBefore = Nothing
        Set aPointAfter = Nothing
        includesIntersection = False
        j = 0
        Do While j < point_list.size
            Set aPoint1 = point_list.At(j)
            If aPoint1.PointDistance > distanceBefore Then
                If aPoint1.PointDistance < distanceAfter Then
                    'In road crossing
                    If aPoint1.IsSwitch Then
                        terminateSurrounding = True
                        point_list.Remove j
                        j = j - 1
                    Else
                        includesIntersection = True
                    End If
                Else
                    'Out of range (far)
                    Set aPointAfter = aPoint1
                    Exit Do
                End If
            Else
                'Out of range (short)
                Set aPointBefore = aPoint1
            End If
            j = j + 1
        Loop
        
        If Not includesIntersection Then
            'Need to add an intersection point between points
            point_list.Add Utils.CreateActionPoint("INTERSECTION", (distanceAfter + distanceBefore) / 2)
        End If
        'Extend intersections around road
        Dim isAPointSwitch As Boolean
        If Not aPointBefore Is Nothing Then 'Not the start of the line
            If aPointBefore.PointType = "INTERSECTION" And Not terminateSurrounding Then 'Point before cross is an intersection and no switch found inside cross
                'Intersection before - need one on the other side
                isAPointSwitch = True
                If aPointAfter Is Nothing Then 'End of the line
                    isAPointSwitch = False
                ElseIf Not aPointAfter.IsSwitch Then 'Not a switch
                    isAPointSwitch = False
                End If
                If Not isAPointSwitch Then
                    'No intersection on other side - add one
                    Set variantIntersectPoint = Utils.CreateActionPoint("INTERSECTION", distanceAfter + 1)
                    variantIntersectPoint.VariantType = Not includesIntersection 'Will be variant if intersection is not strictly required
                    point_list.Add variantIntersectPoint
                End If
            End If
        End If
        If Not aPointAfter Is Nothing Then
            If aPointAfter.PointType = "INTERSECTION" And Not terminateSurrounding Then 'Point after cross is an intersection and no switch found inside cross
                'Intersection before - need one on the other side
                isAPointSwitch = True
                If aPointBefore Is Nothing Then
                    isAPointSwitch = False
                ElseIf Not aPointBefore.IsSwitch Then
                    isAPointSwitch = False
                End If
                If Not isAPointSwitch Then
                    'No intersection on other side - add one
                    Set variantIntersectPoint = Utils.CreateActionPoint("INTERSECTION", distanceBefore - 1)
                    variantIntersectPoint.VariantType = Not includesIntersection 'Will be variant if intersection is not strictly required
                    point_list.Add variantIntersectPoint
                End If
            End If
        End If
        
        'Check if a pole is near one of the points
        Const poleDistance As Double = 4
        For j = 1 To poleIntersections.count
            distance = poleIntersections.item(j)
            If Abs(distance - distanceBefore) < poleDistance Then
                'Pole close to before point
                interestPoint1.VariantType = True 'Make handhole
                Exit For
            ElseIf Abs(distance - distanceAfter) < poleDistance Then
                'Pole close to after point
                interestPoint2.VariantType = True 'Make handhole
                Exit For
            End If
        Next j
        'Make sure at least 1 is a hand hole
        If Not interestPoint1.VariantType Then
            If Not interestPoint2.VariantType Then
                interestPoint1.VariantType = True
            End If
        End If
        
        interestPoint1.NormalForward = False 'Line changes in front
        'Add road switches
        point_list.Add interestPoint1
        point_list.Add interestPoint2
    Next i
    'Sort List because added points will be out of order
    point_list.SortList
    
    'Check if any intersections could be removed
    'Variant intersections were added for a road crossing, but may not be needed if they are surrounded by switch points
    Dim removePoint As Boolean
    i = 0
    Do While i < point_list.size
        removePoint = False
        If i <> 0 Then
            Set aPointBefore = point_list.At(i - 1)
        End If
        If i <> point_list.size - 1 Then
            Set aPointAfter = point_list.At(i + 1)
        End If
        Set interestPoint1 = point_list.At(i)
        
        If interestPoint1.PointType = "INTERSECTION" And interestPoint1.VariantType Then
            If i = 0 Then
                If i = point_list.size - 1 Then
                    'This seems very unlikely, but there is only one point in the list and it is a variant intersection
                    removePoint = True
                ElseIf aPointAfter.IsSwitch Then
                    'Prev point is start & next point is switch
                    removePoint = True
                End If
            ElseIf i = point_list.size - 1 Then
                If aPointBefore.IsSwitch Then
                    'Prev point is a switch & next point is the end
                    removePoint = True
                End If
            ElseIf aPointBefore.IsSwitch And aPointAfter.IsSwitch Then
                'This is the important check
                'Both surrounding points are valid and are switches
                removePoint = True
            End If
        End If
        If removePoint Then
            'Check if there were originally any intersecting points in this line
            If i = 0 Then
                distanceBefore = 0
            Else
                distanceBefore = aPointBefore.PointDistance
            End If
            If i = point_list.size - 1 Then
                distanceAfter = intersectionDistances.item(intersectionDistances.count)
            Else
                distanceAfter = aPointAfter.PointDistance
            End If
            
            For j = 1 To intersectionDistances.count
                distance = intersectionDistances.item(j)
                If distance > distanceBefore And distance < distanceAfter Then
                    'Intersection between two points
                    removePoint = False
                    Exit For
                End If
            Next j
            If removePoint Then
                point_list.Remove i
                i = i - 1
            End If
        End If
        
        i = i + 1
    Loop
    
    'Add Hand holes to bridges
    For i = 1 To bridgeIntersections.count
        Set adjustedPoint1 = Nothing
        Set adjustedPoint2 = Nothing
        distance = bridgeIntersections.item(i)
        Debug.Print "bridge: " & distance
        'Get nearest switch points on both sides and set to hand holes
        
        For j = 0 To point_list.size - 1
            Set aPoint1 = point_list.At(j)
            If aPoint1.IsSwitch Then
                If aPoint1.PointDistance < distance Then
                    'Before bridge
                    If adjustedPoint1 Is Nothing Then
                        Set adjustedPoint1 = Utils.CreateReferencedActionPoint(aPoint1.PointDistance, j)
                    Else
                        If adjustedPoint1.PointDistance < aPoint1.PointDistance Then
                            'New point is closer
                            Set adjustedPoint1 = Utils.CreateReferencedActionPoint(aPoint1.PointDistance, j)
                        End If
                    End If
                Else
                    'After bridge
                    If adjustedPoint2 Is Nothing Then
                        Set adjustedPoint2 = Utils.CreateReferencedActionPoint(aPoint1.PointDistance, j)
                    Else
                        If adjustedPoint2.PointDistance > aPoint1.PointDistance Then
                            'New point is closer
                            Set adjustedPoint2 = Utils.CreateReferencedActionPoint(aPoint1.PointDistance, j)
                        End If
                    End If
                End If
            End If
        Next j
        
        'Set to hand hole
        'If the points aren't defined, then the bridge is at the end of the line, so there will already be a hand hole
        If Not adjustedPoint2 Is Nothing Then
            point_list.SetPointVariant adjustedPoint2.PointReference, True
        End If
        If Not adjustedPoint1 Is Nothing Then
            point_list.SetPointVariant adjustedPoint1.PointReference, True
        End If
        
    Next i
    
    'Add match lines
    'Add temporary switches at start and begining
    point_list.Add Utils.CreateActionPoint("SWITCH", 0), 0
    point_list.Add Utils.CreateActionPoint("SWITCH", intersectionDistances.item(intersectionDistances.count))
    i = 0
    While i < point_list.size - 1
        Set interestPoint1 = point_list.At(i)
        Set interestPoint2 = point_list.At(i + 1)
        For j = 1 To matchIntersections.count
            'Check if match line between 2 points
            distance = matchIntersections.item(j)
            If distance > interestPoint1.PointDistance And distance < interestPoint2.PointDistance Then
                'Between points
                point_list.Add Utils.CreateActionPoint("MATCH", distance), i + 1
                i = i + 1 'Increment i because of the newly added item
                If interestPoint1.PointType = "INTERSECTION" Then
                    'Add intersection after match line
                    point_list.Add Utils.CreateActionPoint("INTERSECTION", distance + 1), i + 1
                    i = i + 1
                ElseIf interestPoint2.PointType = "INTERSECTION" Then
                    'Add intersection before match line
                    point_list.Add Utils.CreateActionPoint("INTERSECTION", distance - 1), i
                    i = i + 1
                End If
            End If
        Next j
        i = i + 1
    Wend
    'Remove temporary switches
    point_list.Remove 0
    point_list.Remove point_list.size - 1
    Set CreateSwitchList = point_list
End Function

Function getSoilInbetween(soilIntersections As Collection, startPoint As Double, endPoint As Double) As Collection
    Dim soilInbetween As New Collection 'Doubles of distances for soils inbetween
    Dim distanceBefore As Double
    Dim distanceAfter As Double
    For j = 1 To soilIntersections.count - 1 Step 2 '2 step because each soil has 2 intersections
        distanceBefore = soilIntersections.item(j)
        distanceAfter = soilIntersections.item(j + 1)
        If distanceBefore > startPoint Then
            If distanceAfter < endPoint Then
                'Between switch points
                soilInbetween.Add distanceBefore
                soilInbetween.Add distanceAfter
            Else
                'Past furthest point
                Exit For
            End If
        End If
    Next j
    Set getSoilInbetween = soilInbetween
End Function

'Returns an adjusted number for the switch point that takes into account the nearby soil patches to place a line
Function getAdjustedSwitchPoint(original As Double, soilInbetween As Collection, MinSoilExtend As Double, MaxSoilExtend As Double, forward As Boolean) As Double
    Dim minFitDistance As Double
    minFitDistance = CDbl(AutoBoreForm.MinBoreFitSize)
    Dim tempPoint As Double
    Dim distanceBefore As Double
    Dim distanceAfter As Double
    tempPoint = original
    If forward Then
        'First switch point
        For j = 1 To soilInbetween.count - 1 Step 2
            distanceBefore = soilInbetween.item(j) 'Soil start
            distanceAfter = soilInbetween.item(j + 1) 'Soil end
            'Check if within minSoilExtend
            If distanceBefore - tempPoint < MinSoilExtend Then
                'Change temp point to soil
                tempPoint = distanceAfter
                If j = soilInbetween.count - 1 Then
                    'Last distance in collection
                    tempPoint = tempPoint + 30
                End If
            Else
                'Too far away
                If j <> 1 Then
                    'Has passed at least 1 soil patch
                    'Move 30 ft from the soil
                    tempPoint = tempPoint + 30
                End If
                Exit For
            End If
            If distanceBefore - original > MaxSoilExtend Then
                'Reached max
                tempPoint = original
                For k = 1 To soilInbetween.count - 1 Step 2
                    distanceBefore = soilInbetween.item(k) 'Soil start
                    distanceAfter = soilInbetween.item(k + 1) 'Soil end
                    If distanceBefore - tempPoint > minFitDistance Then
                        'Fit the switch inbetween
                        tempPoint = tempPoint + ((distanceBefore - tempPoint) / 2)
                        Exit For
                    Else
                        'Can't fit
                        tempPoint = distanceAfter
                    End If
                    If k = soilInbetween.count - 1 Then
                        'Couldn't fit
                        tempPoint = origin
                    End If
                Next k
                Exit For
            End If
        Next j
    Else
        'Second switch point - going backwards
        For j = soilInbetween.count - 1 To 1 Step -2
            distanceBefore = soilInbetween.item(j) 'Soil start
            distanceAfter = soilInbetween.item(j + 1) 'Soil end
            'Check if within minSoilExtend
            If tempPoint - distanceAfter < MinSoilExtend Then
                'Change temp point to soil
                tempPoint = distanceBefore
                If j = 1 Then
                    'Last distance in collection
                    tempPoint = tempPoint - 30
                End If
            Else
                'Too far away
                If j <> soilInbetween.count - 1 Then
                    'Has passed at least 1 soil patch
                    'Move 30 ft from the soil
                    tempPoint = tempPoint - 30
                End If
                Exit For
            End If
            If original - distanceAfter > MaxSoilExtend Then
                'Reached max
                tempPoint = original
                For k = soilInbetween.count - 1 To 1 Step -2
                    distanceBefore = soilInbetween.item(k) 'Soil start
                    distanceAfter = soilInbetween.item(k + 1) 'Soil end
                    If tempPoint - distanceAfter > minFitDistance Then
                        'Fit the switch inbetween
                        tempPoint = tempPoint - ((distanceAfter - tempPoint) / 2)
                        Exit For
                    Else
                        'Can't fit
                        tempPoint = distanceBefore
                    End If
                    If k = 1 Then
                        'Couldn't fit
                        tempPoint = origin
                    End If
                Next k
                Exit For
            End If
        Next j
    End If
    getAdjustedSwitchPoint = tempPoint
End Function


'Get the points anong mainLine that have poles nearby
'Returns a Collection of Doubles as distances
Function getPoleIntersections(mainLine As ComplexStringElement) As Collection
    Dim maxPoleDistance As Double 'Maximum distance the pole can be from the mainLine
    maxPoleDistance = CDbl(AutoBoreForm.MaxPoleRWDistance) + 4
    Dim intersections As New Collection 'Collection of Point3d objects
    
    Dim oElement As Element
    'Scan for pole cell
    Dim oScanCriteria As ElementScanCriteria
    Set oScanCriteria = New ElementScanCriteria
    oScanCriteria.ExcludeAllTypes
    'oScanCriteria.IncludeType msdElementTypeSharedCell
    oScanCriteria.IncludeType msdElementTypeCellHeader
    oScanCriteria.IncludeType msdElementTypeText
    Dim oScanEnumerator As ElementEnumerator
    Set oScanEnumerator = ActiveModelReference.Scan(oScanCriteria)
    'Iterate through results
    Dim projectedPoint As Point3d
    Dim distance As Double
    Dim rayLine As LineElement
    Dim origin As Point3d
    Dim isPole As Boolean

    While oScanEnumerator.MoveNext
        Set oElement = oScanEnumerator.Current
        isPole = False
        If oElement.IsCellElement Then
            If oElement.AsCellElement.name = "EXIST UTILITIES POWER JOINT USE TELEPHONE" Then
                isPole = True
                origin = oElement.AsCellElement.origin
            End If
        ElseIf oElement.IsTextElement Then
            If oElement.Level.name = "Sheet Symbology CELL" Then
                isPole = True
                origin = oElement.AsTextElement.origin
            End If
        End If
        
        If isPole Then
            projectedPoint = mainLine.ProjectPointOnPerpendicular2(origin, Matrix3dIdentity)
            distance = Point3dDistance(origin, projectedPoint)
            If distance < maxPoleDistance Then
                'Draw line between pole and projected point
                'Check intersections of that line, if there is a centerline, then don't add
                Set rayLine = CreateLineElement2(Nothing, projectedPoint, origin)
                
                If Not isIntersectingCenterline(rayLine) Then
                    'Add to collection
                    intersections.Add projectedPoint
                    'Debug.Print "Point: " & projectedPoint.x & " " & projectedPoint.y
                End If
            End If
        End If
    Wend
    Set getPoleIntersections = ConvertToDistances(mainLine, intersections)
End Function

'Get the points anong mainLine that have guardrails nearby
'Returns a Collection of Doubles as distances
Function getGuardrailIntersections(mainLine As ComplexStringElement) As Collection
    Dim maxGuardRailDistance As Double 'Maximum distance the guardrail can be from the mainLine
    maxGuardRailDistance = CDbl(AutoBoreForm.MinGuardrailPlow)
    Dim intersections As New Collection 'Collection of Point3d objects
    
    Dim oElement As Element
    'Scan for pole cell
    Dim oScanCriteria As ElementScanCriteria
    Set oScanCriteria = New ElementScanCriteria
    oScanCriteria.ExcludeAllTypes
    'oScanCriteria.IncludeType msdElementTypeSharedCell
    oScanCriteria.IncludeType msdElementTypeCellHeader
    Dim oScanEnumerator As ElementEnumerator
    Set oScanEnumerator = ActiveModelReference.Scan(oScanCriteria)
    'Iterate through results
    Dim projectedPoint As Point3d
    Dim distance As Double
    Dim rayLine As LineElement
    Dim origin As Point3d
    Dim isGuardrail As Boolean

    While oScanEnumerator.MoveNext
        Set oElement = oScanEnumerator.Current
        isGuardrail = False

        If oElement.IsCellElement Then
        If oElement.AsCellElement.name <> "" Then
            If oElement.AsCellElement.name = "M350 GRAU AP" Then

                isGuardrail = True
                origin = oElement.AsCellElement.origin
            End If
            End If
        End If
        
        If isGuardrail Then
            projectedPoint = mainLine.ProjectPointOnPerpendicular2(origin, Matrix3dIdentity)
            distance = Point3dDistance(origin, projectedPoint)
            If distance < maxGuardRailDistance Then
                'Draw line between guardrail and projected point
                'Check intersections of that line, if there is a centerline, then don't add
                Set rayLine = CreateLineElement2(Nothing, projectedPoint, origin)
                
                If Not isIntersectingCenterline(rayLine) Then
                    'Add to collection
                    intersections.Add projectedPoint
                    'Debug.Print "Point: " & projectedPoint.x & " " & projectedPoint.y
                End If
            End If
        End If
    Wend
    Set getGuardrailIntersections = ConvertToDistances(mainLine, intersections)
End Function

'Returns if the line element is intersecting a centerline element
Function isIntersectingCenterline(rayLine As LineElement) As Boolean
    Dim intersections As Integer
    intersections = 0
    Dim oElement As Element
    Dim centerLine As String
    centerLine = AutoBoreForm.CenterlineLevel

    Dim oScanCriteria As ElementScanCriteria
    Set oScanCriteria = New ElementScanCriteria
    oScanCriteria.ExcludeAllLevels
    oScanCriteria.IncludeLevel ActiveModelReference.Levels(centerLine)
    Dim oScanEnumerator As ElementEnumerator
    Set oScanEnumerator = ActiveModelReference.Scan(oScanCriteria)
    Dim intersectionPoints() As Point3d
    Dim iPoint As Point3d
    While oScanEnumerator.MoveNext
        Set oElement = oScanEnumerator.Current
        If oElement.IsIntersectableElement Then
            intersectionPoints = rayLine.GetIntersectionPoints(oElement.AsIntersectableElement, Matrix3dIdentity)
            If UBound(intersectionPoints) <> -1 Then
                'Has intersection
                isIntersectingCenterline = True
                Exit Function
            End If
        End If
    Wend
    isIntersectingCenterline = False
End Function

'Get the points at which match lines intersect
'Returns a collection of Double distances
Function getMatchIntersections(mainLine As ComplexStringElement) As Collection
    Dim intersections As New Collection 'Collection of Point3d objects
    Dim intersectionsIndex
    Dim matchLineLevel As Level
    Set matchLineLevel = ActiveModelReference.Levels("Matchline")
    Dim oElement As Element
    'Scan for match level
    Dim oScanCriteria As ElementScanCriteria
    Set oScanCriteria = New ElementScanCriteria
    oScanCriteria.ExcludeAllLevels
    oScanCriteria.IncludeLevel matchLineLevel
    oScanCriteria.ExcludeAllTypes
    oScanCriteria.IncludeType msdElementTypeLine
    Dim oScanEnumerator As ElementEnumerator
    Set oScanEnumerator = ActiveModelReference.Scan(oScanCriteria)
    'Iterate through elements
    Dim intersectionPoints() As Point3d
    Dim iPoint As Point3d
    While oScanEnumerator.MoveNext
        Set oElement = oScanEnumerator.Current
        If oElement.IsIntersectableElement Then
            intersectionPoints = mainLine.GetIntersectionPoints(oElement, Matrix3dIdentity)
            If UBound(intersectionPoints) <> -1 Then
                'Has intersection
                'Add intersection points to collection
                For i = 0 To UBound(intersectionPoints)
                    iPoint = intersectionPoints(i)
                    intersectionsIndex = intersectionsIndex + 1
                    intersections.Add item:=iPoint, key:=CStr(intersectionsIndex)
                    'Debug.Print "Point: " & iPoint.x & " " & iPoint.y
                Next i
            End If
        End If
    Wend
    Set getMatchIntersections = ConvertToDistances(mainLine, intersections)
End Function

Function getCenterLineIntersections(mainLine As ComplexStringElement) As Collection
    Dim intersections As New Collection 'Collection of Point3d objects
    Dim centerLevel As String
    centerLevel = AutoBoreForm.CenterlineLevel
    Dim oElement As Element
    Dim oScanCriteria As ElementScanCriteria
    Set oScanCriteria = New ElementScanCriteria
    oScanCriteria.ExcludeAllLevels
    oScanCriteria.IncludeLevel ActiveModelReference.Levels(centerLevel)
    Dim oScanEnumerator As ElementEnumerator
    Set oScanEnumerator = ActiveModelReference.Scan(oScanCriteria)
    'Iterate through elements
    Dim intersectionPoints() As Point3d
    Dim iPoint As Point3d
    While oScanEnumerator.MoveNext
        Set oElement = oScanEnumerator.Current
        If oElement.IsIntersectableElement Then
            intersectionPoints = mainLine.GetIntersectionPoints(oElement, Matrix3dIdentity)
            If UBound(intersectionPoints) <> -1 Then
                'Has intersection
                'Add intersection points to collection
                For i = 0 To UBound(intersectionPoints)
                    iPoint = intersectionPoints(i)
                    intersections.Add iPoint
                    'Debug.Print "Point: " & iPoint.x & " " & iPoint.y
                Next i
            End If
        End If
    Wend
    Set getCenterLineIntersections = ConvertToDistances(mainLine, intersections)
End Function

'Returns a collection of 3d points
Function getDrivewayIntersections(mainLine As ComplexStringElement) As Collection
    Dim intersections As New Collection 'Collection of Point3d objects
    Dim roadLevel As Level
    Set roadLevel = ActiveModelReference.Levels("Exist Roads EOP")
    Dim oElement As Element
    'Scan for road level
    Dim oScanCriteria As ElementScanCriteria
    Set oScanCriteria = New ElementScanCriteria
    oScanCriteria.ExcludeAllLevels
    oScanCriteria.IncludeLevel roadLevel
    Dim oScanEnumerator As ElementEnumerator
    Set oScanEnumerator = ActiveModelReference.Scan(oScanCriteria)
    'Iterate through elements
    Dim intersectionPoints() As Point3d
    Dim iPoint As Point3d
    While oScanEnumerator.MoveNext
        Set oElement = oScanEnumerator.Current
        If oElement.IsIntersectableElement Then
            intersectionPoints = mainLine.GetIntersectionPoints(oElement, Matrix3dIdentity)
            If UBound(intersectionPoints) <> -1 Then
                'Has intersection
                'Add intersection points to collection
                For i = 0 To UBound(intersectionPoints)
                    iPoint = intersectionPoints(i)
                    intersections.Add iPoint
                    'Debug.Print "Point: " & iPoint.x & " " & iPoint.y
                Next i
            End If
        End If
    Wend
    Dim sortedIntersections As Collection
    Set sortedIntersections = ConvertToDistances(mainLine, intersections)
    Dim distanceBefore As Double
    Dim distanceAfter As Double
    
    'Remove any roads that  have a centerline between them
    Dim centerLineIntersections As Collection
    Set centerLineIntersections = getCenterLineIntersections(mainLine)
    Dim removeIndicies As New Collection
    For i = 1 To sortedIntersections.count - 1 Step 2
        distanceBefore = sortedIntersections.item(i)
        distanceAfter = sortedIntersections.item(i + 1)
        For j = 1 To centerLineIntersections.count
            If centerLineIntersections.item(j) > distanceBefore Then
                If centerLineIntersections.item(j) < distanceAfter Then
                    'Between road lines
                    removeIndicies.Add i
                End If
                Exit For 'This is required to exit the loop so multiple indicies won't be added if there are more than 1 centerline
            End If
        Next j
    Next i
    'Remove roads
    For i = 1 To removeIndicies.count
        sortedIntersections.Remove removeIndicies.item(i) - (i * 2 - 2)
        sortedIntersections.Remove removeIndicies.item(i) - (i * 2 - 2)
    Next i
    Set intersections = Nothing
    'Convert back into points
    For i = 1 To sortedIntersections.count
        intersections.Add mainLine.PointAtDistance(sortedIntersections.item(i))
    Next i
    
    Set getDrivewayIntersections = intersections
End Function

'Get road intersections that intersect the mainLine. The line must pass through the centerline
'Points returned are NOT where the roads are at, but instead where the line begins to cross the road
'Returns a collection of distances as doubles
Function getRoadIntersections(mainLine As ComplexStringElement) As Collection
    Dim intersections As New Collection 'Collection of Point3d objects
    Dim roadLevel As Level
    Set roadLevel = ActiveModelReference.Levels("Exist Roads EOP")
    Dim soilLevel As Level
    Set soilLevel = ActiveModelReference.Levels("Exist Roads Soil")
    Dim oElement As Element
    'Scan for road level
    Dim oScanCriteria As ElementScanCriteria
    Set oScanCriteria = New ElementScanCriteria
    oScanCriteria.ExcludeAllLevels
    oScanCriteria.IncludeLevel roadLevel
    oScanCriteria.IncludeLevel soilLevel
    Dim oScanEnumerator As ElementEnumerator
    Set oScanEnumerator = ActiveModelReference.Scan(oScanCriteria)
    'Iterate through elements
    Dim intersectionPoints() As Point3d
    Dim iPoint As Point3d
    While oScanEnumerator.MoveNext
        Set oElement = oScanEnumerator.Current
        If oElement.IsIntersectableElement Then
            intersectionPoints = mainLine.GetIntersectionPoints(oElement, Matrix3dIdentity)
            If UBound(intersectionPoints) <> -1 Then
                'Has intersection
                'Add intersection points to collection
                For i = 0 To UBound(intersectionPoints)
                    iPoint = intersectionPoints(i)
                    intersections.Add iPoint
                    'Debug.Print "Point: " & iPoint.x & " " & iPoint.y
                Next i
            End If
        End If
    Wend
    Dim sortedIntersections As Collection
    Set sortedIntersections = ConvertToDistances(mainLine, intersections)
    Set intersections = Nothing
    Dim distanceBefore As Double
    Dim distanceAfter As Double
    
    'Remove any roads that don't have a centerline between them
    Dim centerLineIntersections As Collection
    Set centerLineIntersections = getCenterLineIntersections(mainLine)
    Dim removeIndicies As New Collection
    Dim between As Boolean
    For i = 1 To sortedIntersections.count - 1 Step 2
        distanceBefore = sortedIntersections.item(i)
        distanceAfter = sortedIntersections.item(i + 1)
        between = False
        For j = 1 To centerLineIntersections.count
            If centerLineIntersections.item(j) > distanceBefore Then
                If centerLineIntersections.item(j) < distanceAfter Then
                    If distanceAfter - distanceBefore > 10 Then
                        'Between Road Lines
                        between = True
                    End If
                End If
                Exit For 'This is required to exit the loop before a center line appears that is after the roads
            End If
        Next j
        If Not between Then
            removeIndicies.Add i
        End If
    Next i
    'Remove roads
    For i = 1 To removeIndicies.count
        sortedIntersections.Remove removeIndicies.item(i) - (i * 2 - 2)
        sortedIntersections.Remove removeIndicies.item(i) - (i * 2 - 2)
    Next i
    
    Dim pointBefore As Point3d
    Dim pointAfter As Point3d
    Dim MaxRWDistance As Double
    MaxRWDistance = CDbl(AutoBoreForm.MaxRWDistance)
    Dim RW1 As Point3d
    Dim RW2 As Point3d
    Dim RW1Distance As Double
    Dim RW2Distance As Double
    Dim projectedPointBefore As Point3d
    Dim projectedPointAfter As Point3d
    Dim projectedDistance As Double
    Dim nearby As Collection
    'Iterate through sorted list
    For i = 1 To sortedIntersections.count - 1 Step 2
        distanceBefore = sortedIntersections.item(i)
        distanceAfter = sortedIntersections.item(i + 1)
        pointBefore = mainLine.PointAtDistance(distanceBefore)
        pointAfter = mainLine.PointAtDistance(distanceAfter)
        'Get nearby R/W
        RW1Distance = -1
        RW2Distance = -1
        Set nearby = Utils.NearbyElements(pointBefore, MaxRWDistance)
        For j = 1 To nearby.count
            Set oElement = nearby.item(j)
            If oElement.IsGraphical And oElement.IsIntersectableElement Then
                If oElement.Level.name = "Exist Right of Way Line" Then
                    'R/W element
                    projectedPointBefore = oElement.AsIntersectableElement.ProjectPointOnPerpendicular2(pointBefore, Matrix3dIdentity)
                    projectedPointAfter = oElement.AsIntersectableElement.ProjectPointOnPerpendicular2(pointAfter, Matrix3dIdentity)
                    If Point3dDistance(projectedPointBefore, pointBefore) < Point3dDistance(projectedPointAfter, pointAfter) Then
                        'Before point is closer
                        projectedDistance = Point3dDistance(projectedPointBefore, pointBefore)
                        If RW1Distance = -1 Then
                            'Nothing set yet
                            RW1Distance = projectedDistance
                            RW1 = projectedPointBefore
                        Else
                            If projectedDistance < RW1Distance Then
                                'Closer than prev RW1
                                RW1Distance = projectedDistance
                                RW1 = projectedPointBefore
                            End If
                        End If
                    Else
                        'After point is closer
                        projectedDistance = Point3dDistance(projectedPointAfter, pointAfter)
                        If RW2Distance = -1 Then
                            'Nothing set yet
                            RW2Distance = projectedDistance
                            RW2 = projectedPointAfter
                        Else
                            If projectedDistance < RW2Distance Then
                                'Closer than prev RW2
                                RW2Distance = projectedDistance
                                RW2 = projectedPointAfter
                            End If
                        End If
                    End If
                End If
            End If
        Next j
        If RW2Distance <> -1 And RW1Distanced <> -1 Then
            'Found at least 2 R/W
            'Add their projected points to the intersections
            intersections.Add mainLine.ProjectPointOnPerpendicular2(RW1, Matrix3dIdentity)
            intersections.Add mainLine.ProjectPointOnPerpendicular2(RW2, Matrix3dIdentity)
        Else
            'Not Enough R/W Found
            MessageCenter.AddMessage "Bore Pit Unsuccesfully Created", "Could not find 2 R/W elements on road crossing: x=" & pointBefore.x & " y=" & pointBefore.y, msdMessageCenterPriorityError, True
        End If
    Next i
    
    Set getRoadIntersections = ConvertToDistances(mainLine, intersections)
End Function

'Get the soil lines that are directly intersecting the main line
'Assuming the mainLine doesn't start or stop inside soil, the inside and outside of soil patches can be found
'There is soil between odd numbered indicies and the even number after it (index at 1)
'Returns a collection of Double distances
Function getSoilIntersections(mainLine As ComplexStringElement) As Collection
    Dim intersections As New Collection 'Collection of Point3d objects
    Dim soilLevel As Level
    Set soilLevel = ActiveModelReference.Levels("Exist Roads Soil")
    Dim oElement As Element
    'Scan for soil level
    Dim oScanCriteria As ElementScanCriteria
    Set oScanCriteria = New ElementScanCriteria
    oScanCriteria.ExcludeAllLevels
    oScanCriteria.IncludeLevel soilLevel
    Dim oScanEnumerator As ElementEnumerator
    Set oScanEnumerator = ActiveModelReference.Scan(oScanCriteria)
    
    'Iterate through elements
    Dim intersectionPoints() As Point3d
    Dim iPoint As Point3d
    While oScanEnumerator.MoveNext
        Set oElement = oScanEnumerator.Current
        If oElement.IsIntersectableElement Then
            intersectionPoints = mainLine.GetIntersectionPoints(oElement, Matrix3dIdentity)
            If UBound(intersectionPoints) <> -1 Then
                'Has intersection
                'Add intersection points to collection
                For i = 0 To UBound(intersectionPoints)
                    iPoint = intersectionPoints(i)
                    intersections.Add iPoint
                    'Debug.Print "Point: " & iPoint.x & " " & iPoint.y
                Next i
            End If
        End If
    Wend
    Set getSoilIntersections = ConvertToDistances(mainLine, intersections)
End Function

'Convert intersectionPoints on mainLine to distances between them along the element
'Return a collection of doubles that represent distance from the start point
Function ConvertToDistances(mainLine As ComplexStringElement, intersectionPoints As Collection) As Collection
    Dim distances As New Collection
    Dim distancesIndex
    Dim distanceArray() As Double
    ReDim distanceArray(intersectionPoints.count)
    Dim point As Point3d
    'Iterate through intersection
    For i = 1 To intersectionPoints.count
        point = intersectionPoints.item(i)
        distanceArray(i - 1) = mainLine.DistanceAtPoint(point)
        'Debug.Print "Point: " & point.x & " " & point.y
        'Debug.Print distanceArray(i - 1)
    Next i
    'Sort array
    Arrays.QuickSort distanceArray, 0, intersectionPoints.count - 1
    'Convert Array to Collection
    For i = 1 To intersectionPoints.count
        distancesIndex = distancesIndex + 1
        distances.Add item:=distanceArray(i - 1), key:=CStr(distancesIndex)
    Next i
    Set ConvertToDistances = distances
End Function


'Get the intersecting points of the edges of a bridge element
Function getIntersectingBridges(mainLine As ComplexStringElement) As Collection
    'How many points per bridge
    'Points come from the closest verticies being projected onto the mainLine
    Dim intersectionsPerBridge As Integer
    intersectionsPerBridge = 2
    'Max distance the verticies can be from the bridge
    Dim maxDistance As Double
    maxDistance = CDbl(AutoBoreForm.MaxBridgeDistance)
    Dim intersectingPoints As New Collection
    Dim intersectingPointsIndex
    Dim bridgeLevel As Level
    On Error Resume Next
    Set bridgeLevel = ActiveDesignFile.Levels("Prop Roadway Bridge")
    If bridgeLevel Is Nothing Then
        Set getIntersectingBridges = intersectingPoints
        Exit Function
    End If
    Dim oElement As Element
    'Scan for bridge level
    Dim oScanCriteria As ElementScanCriteria
    Set oScanCriteria = New ElementScanCriteria
    oScanCriteria.ExcludeAllLevels
    oScanCriteria.IncludeLevel bridgeLevel
    Dim oScanEnumerator As ElementEnumerator
    Set oScanEnumerator = ActiveModelReference.Scan(oScanCriteria)
    'Iterate through elements
    Dim verticies() As Point3d
    Dim distancesToMain() As Double
    Dim projectedPoints() As Point3d
    Dim closestPoint As Point3d
    Dim closestParameter As Double
    Dim distance As Double
    Dim closestVertexIntersectionIndex() As Integer
    ReDim closestVertexIntersectionIndex(intersectionsPerBridge)
    Dim tempIndex As Integer
    Dim tempIndex2 As Integer
    While oScanEnumerator.MoveNext
        Set oElement = oScanEnumerator.Current
        'Make sure it is a shape
        If oElement.IsShapeElement Then
            'Get the verteces of the shape
            ReDim verticies(oElement.AsShapeElement.VerticesCount)
            verticies = oElement.AsShapeElement.GetVertices
            ReDim distancesToMain(oElement.AsShapeElement.VerticesCount)
            ReDim projectedPoints(oElement.AsShapeElement.VerticesCount)
            'Set the minimimum distance as the first distance - assuming shapes must have at least 2 verticies
            'Iterate through all verticies
            closestVertexIntersectionIndex(0) = 0
            For i = 0 To oElement.AsShapeElement.VerticesCount - 2 'Not reading the last vertex because it is the same as the first
                'Get distance to main line
                projectedPoints(i) = mainLine.ProjectPointOnPerpendicular2(verticies(i), Matrix3dIdentity)
                distancesToMain(i) = Point3dDistance(verticies(i), projectedPoints(i))
                'Get closest intersections
                'Check if closer than any of the other verticies
                    For j = 0 To Utils.Min(intersectionsPerBridge - 1, i)
                        'j is the index of closestVertexIntersectionIndex
                        'i is the new "index" that needs to replace whatever is at j
                        If distancesToMain(i) < distancesToMain(j) Then
                            'Shift closestVertexIntersections forward
                            tempIndex = closestVertexIntersectionIndex(j)
                            closestVertexIntersectionIndex(j) = i
                            For k = j + 1 To Utils.Min(intersectionsPerBridge - 1, i)
                                'Shift everything forward
                                If k <> Utils.Min(intersectionsPerBridge - 1, i) Then 'Won't be getting unset data
                                    tempIndex2 = closestVertexIntersectionIndex(k)
                                End If
                                closestVertexIntersectionIndex(k) = tempIndex
                                tempIndex = tempIndex2
                            Next k
                            Exit For
                        End If
                    Next j
            Next i
            'closestVertexIntersectionIndex is now set to have the index of only the closest verticies
            For i = 0 To intersectionsPerBridge - 1
                'Make sure the distance is within the max set, otherwise this bridge may not even be in the bore path
                If distancesToMain(closestVertexIntersectionIndex(i)) < maxDistance Then
                    'Add projected point
                    closestPoint = projectedPoints(closestVertexIntersectionIndex(i))
                    intersectingPointsIndex = intersectingPointsIndex + 1
                    intersectingPoints.Add item:=closestPoint, key:=CStr(intersectingPointsIndex)
                    'Debug.Print "Point: " & closestPoint.x & " " & closestPoint.y
                End If
            Next i
        End If
    Wend
    Set getIntersectingBridges = intersectingPoints
End Function

'Gets any culverts that are intersecting the road and would be a problem for the plow line
'Return a collection of intersecting points as Point3d objects
Function getIntersectingCulverts(mainLine As ComplexStringElement) As Collection
    Dim culvertMaxDistance As Double
    culvertMaxDistance = CDbl(AutoBoreForm.MaxCulvertDistance)
    Dim intersectingPoints As New Collection
    Dim intersectingPointsIndex
    Dim roadElements As New Collection 'A collection of intersectable objects
    Dim oElement As Element
    Dim centerLine As String
    centerLine = AutoBoreForm.CenterlineLevel
    'Get all Roads EOP elements
    Dim oScanCriteria As ElementScanCriteria
    Set oScanCriteria = New ElementScanCriteria
    oScanCriteria.ExcludeAllLevels
    oScanCriteria.IncludeLevel ActiveDesignFile.Levels(centerLine)
    Dim oScanEnumerator As ElementEnumerator
    Set oScanEnumerator = ActiveModelReference.Scan(oScanCriteria)
    'Add all to roadElements collection
    Dim index
    While oScanEnumerator.MoveNext
        Set oElement = oScanEnumerator.Current
        If oElement.IsIntersectableElement Then
            index = index + 1
            roadElements.Add item:=oElement.AsIntersectableElement, key:=CStr(index)
        End If
    Wend
    'Iterate through all orange elements and get ones that start with culvertText
    Set oScanCriteria = New ElementScanCriteria
    'Prepare criteria
    oScanCriteria.ExcludeAllTypes
    oScanCriteria.IncludeType msdElementTypeLine
    oScanCriteria.IncludeType msdElementTypeLineString
    oScanCriteria.ExcludeAllLevels
    Dim pipeLevels As Collection
    Set pipeLevels = getPipeLevels() 'Get all pipe levels that begin with the Exist Structure Minor Pipes
    'Add all to the included levels
    For i = 1 To pipeLevels.count
        oScanCriteria.IncludeLevel pipeLevels.item(i)
    Next i
    'Scan
    Set oScanEnumerator = ActiveModelReference.Scan(oScanCriteria)
    'Iterate through scan
    Dim extendedElement As LineElement
    Dim startPoint As Point3d
    Dim endPoint As Point3d
    Dim intersections() As Point3d
    Dim culvertLine As LineElement
    While oScanEnumerator.MoveNext
        Set culvertLine = oScanEnumerator.Current
        If culvertLine.IsLineElement Then
            'Break up into segments
            For j = 2 To culvertLine.AsLineElement.VerticesCount
            Set oElement = CreateLineElement2(Nothing, culvertLine.AsLineElement.Vertex(j - 1), culvertLine.AsLineElement.Vertex(j))
            
            'A culvert object
            'Check if intersecting the Exist Roads EOP level
            If DoesIntersect(roadElements, oElement.AsIntersectableElement) Then
                'Intersects the road
                'Get a copy and extend it by 50 feet or so to make sure it will intersect the main line
                Set extendedElement = ExtendLine(oElement.AsLineElement, culvertMaxDistance)
                'Check if intersecting main line
                 intersections = extendedElement.GetIntersectionPoints(mainLine, Matrix3dIdentity)
                If UBound(intersections) <> -1 Then
                    'Has intersection
                    'Add intersection points to collection
                    Dim iPoint As Point3d
                    For i = 0 To UBound(intersections)
                        iPoint = intersections(i)
                        intersectingPointsIndex = intersectingPointsIndex + 1
                        intersectingPoints.Add item:=iPoint, key:=CStr(intersectingPointsIndex)
                        'Debug.Print "Point: " & iPoint.X & " " & iPoint.Y
                    Next i
                End If
            End If
            Next j
        End If
    Wend
    Set getIntersectingCulverts = intersectingPoints
End Function

'Returns if oElement intersects any of the roadElements
Function DoesIntersect(roadElements As Collection, oElement As IntersectableElement) As Boolean
    Dim roadElement As IntersectableElement
    Dim intersections() As Point3d
    For Each roadElement In roadElements
        intersections = roadElement.GetIntersectionPoints(oElement, Matrix3dIdentity)
        If UBound(intersections) <> -1 Then
            'Has intersection
            DoesIntersect = True
            Exit Function
        End If
    Next roadElement
    DoesIntersect = False
End Function

'Returns an extended line by length on both sides
Function ExtendLine(original As LineElement, length As Double) As LineElement
    Dim el As LineElement
    Set el = original.Clone

    'Extend start
    Dim segmentVector As Point3d
    segmentVector = Point3dSubtract(el.Vertex(1), el.Vertex(2))
    segmentVector = Point3dNormalize(segmentVector)
    segmentVector = Point3dScale(segmentVector, length)
    
    Dim newStartPoint As Point3d
    newStartPoint = Point3dAdd(el.Vertex(1), segmentVector)
    el.ModifyVertex 0, newStartPoint
    
    'Extend end
    Dim numOfVertices As Integer
    numOfVertices = el.VerticesCount
    
    segmentVector = Point3dSubtract(el.Vertex(numOfVertices), el.Vertex(numOfVertices - 1))
    segmentVector = Point3dNormalize(segmentVector)
    segmentVector = Point3dScale(segmentVector, length)
    
    Dim newEndPoint As Point3d
    newEndPoint = Point3dAdd(el.Vertex(numOfVertices), segmentVector)
    el.ModifyVertex numOfVertices - 1, newEndPoint
    
    Set ExtendLine = el
End Function

'Get all of the levels in the active model reference that begin with the culvert text
'Returns a collection of Level objects
Function getPipeLevels() As Collection
    Const culvertText As String = "Exist Structure Minor Pipes"
    Dim lvl As Level
    Dim allLevels As New Collection
    For Each lvl In ActiveModelReference.Levels
        If Utils.startsWith(lvl.name, culvertText) And InStr(lvl.name, "Text") = 0 Then
            allLevels.Add item:=lvl
            'Debug.Print lvl.Name
        End If
        If lvl.name = "Exist Structure Minor Head and End Wall" Then
            allLevels.Add item:=lvl
        End If
    Next
    Set getPipeLevels = allLevels
End Function

'Returns the closest interescting point before or after the distance
'Returns Nothing if the end of the list comes first
Function getNearbyIntersectingPoint(intersectionDistances As Collection, distance As Double, after As Boolean) As Double
    Dim closest As Double
    Dim interestPoint As Double
    closest = -75
    Dim i As Long
    For i = 1 To intersectionDistances.count
        interestPoint = intersectionDistances.item(i)
        If interestPoint > distance And Not after Then
            'Past distance - return closest
            Exit For
        End If
        closest = interestPoint
        'Add 75 when it hits the last item (end of list)
        If i = intersectionDistances.count Then closest = closest + 75
        If interestPoint > distance And after Then
            'Past distance - return closest
            Exit For
        End If
    Next i
    getNearbyIntersectingPoint = closest
End Function

Attribute VB_Name = "CreateComplexString"
Function CreateComplexString()
    Debug.Print "CreateComplexString Start"
    'Get starting element from selection
    If Not ActiveModelReference.AnyElementsSelected Then
        MsgBox "The macro requires a selection set"
        Exit Function
    End If
    Dim ee As ElementEnumerator
    Set ee = ActiveModelReference.GetSelectedElements 'Selected elements
    ee.Reset
    ee.MoveNext 'Move to the first element
    'Check if it is a line
    If ee.Current.Type <> msdElementTypeLine Then
        MsgBox "The macro requires a line selection" + ee.Current.Type
        Exit Function
    End If
    
    'Get complex chain from connected elements
    Dim complexChain As ComplexStringElement
    Set complexChain = CombineLines(ee.Current.AsLineElement)
    

End Function


'I'm confused about collection keys and their indicies - Do they index at 0?
'Can I get a chainable element out of a collection that holds line elements?
Function CombineLines(startingElement As LineElement) As ComplexStringElement
    'getConnectedLines for both sides of the starting element
    'The starting point lines will be at the begining of the array and will need to be in reversed order
    Dim startPointLines As Collection
    Dim endPointLines As Collection
    Dim allLines() As ChainableElement
    Set startPointLines = getConnectedLines(startingElement, True)
    Set endPointLines = getConnectedLines(startingElement, False)
    'Set to propper size
    Dim numElements As Integer
    numElements = startPointLines.count + endPointLines.count + 1
    Debug.Print "Number of elements: " & numElements
    ReDim allLines(numElements)
    Dim allLinesIndex As Integer
    allLinesIndex = 0
    'Add all start point lines to allLines but in reverse
    For i = startPointLines.count To 1 Step -1
        Set allLines(allLinesIndex) = startPointLines.item(i)
        Debug.Print "S: " & i & " " & allLines(allLinesIndex).startPoint.x & " " & allLines(allLinesIndex).startPoint.y
        allLinesIndex = allLinesIndex + 1
    Next i
    'Add startingElement to allLines
    Set allLines(allLinesIndex) = startingElement
    Debug.Print "M: " & allLines(allLinesIndex).startPoint.x & " " & allLines(allLinesIndex).startPoint.y
    allLinesIndex = allLinesIndex + 1
    'Add all end point lines to allLines
    For i = 1 To endPointLines.count
        Set allLines(allLinesIndex) = endPointLines.item(i)
        Debug.Print "E: " & i & " " & allLines(allLinesIndex).startPoint.x & " " & allLines(allLinesIndex).startPoint.y
        allLinesIndex = allLinesIndex + 1
    Next i
    
    'Now, all lines connected to the starting element should be in the allLines and ordered properly
    Set CombineLines = PlaceComplexString(allLines, numElements)
    
End Function

'Get the line elements of the same level that are connected
'startPoint controls whether the start point of the given line element should be used
'Returns a collection of LineElement objects
Function getConnectedLines(line As LineElement, startPoint As Boolean) As Collection
    Dim nearby As Collection
    Dim connectionPoint As Point3d
    Dim connectedLines As New Collection
    'Define connection point based on if it should be the start point or not
    If startPoint Then
        connectionPoint = line.startPoint
    Else
        connectionPoint = line.endPoint
    End If
    Set nearby = NearbyElements(connectionPoint, 0.025)
    Dim nearbyElement As Element
    Dim connectedLinesIndex
    Dim additionalLines As Collection
    Dim additionalLineStartPoint As Boolean
    Dim subElement As LineElement
    'Iterate through nearby elements
    For Each nearbyElement In nearby
        Debug.Print "Element"
        'Check if it is a line element
        If nearbyElement.IsLineElement Then
            Debug.Print "Line"
            'Check if it has the same level
            If nearbyElement.AsLineElement.Level.ID = line.Level.ID Then
                'Check if it is not the same object as lineElement
                If DLongToString(nearbyElement.ID) <> DLongToString(line.ID) Then
                    'Add to connectedLines
                    connectedLinesIndex = connectedLinesIndex + 1
                    connectedLines.Add item:=nearbyElement, key:=CStr(connectedLinesIndex)
                    'Add all of its connecting lines
                    'First check if the starting point or the ending point is closer to connectionPoint
                    'We want to use the one further away so we don't get the same elements
                    additionalLineStartPoint = Point3dDistance(connectionPoint, nearbyElement.AsLineElement.startPoint) > Point3dDistance(connectionPoint, nearbyElement.AsLineElement.endPoint)
                    Set additionalLines = getConnectedLines(nearbyElement.AsLineElement, additionalLineStartPoint)
                    'Add all into connectedLines
                    For Each subElement In additionalLines
                        connectedLinesIndex = connectedLinesIndex + 1
                        connectedLines.Add item:=subElement, key:=CStr(connectedLinesIndex)
                    Next subElement
                End If
            End If
        End If
    Next nearbyElement
    Set getConnectedLines = connectedLines
End Function


'Place a complex string in the active model using an array of chainable elements
'The created element is assigned to oComplexString
Function PlaceComplexString(lineElements() As ChainableElement, numElements As Integer) As ComplexStringElement
    If numElements < 2 Then
        Exit Function
    End If
    'Align first line to have its end point as the point connected
    If Point3dDistance(lineElements(0).endPoint, lineElements(1).startPoint) > 0.025 And Point3dDistance(lineElements(0).endPoint, lineElements(1).endPoint) > 0.025 Then
        'End Point is not lined up
        
    End If
    'Need to redefine the line elements so that their start and end points match up
    For i = 1 To numElements - 1
        'Align elements by the direction of the first one
        'If Point3dDistance(connectionPoint, nearbyElement.AsLineElement.startPoint) > Point3dDistance(connectionPoint, nearbyElement.AsLineElement.EndPoint) Then
            'Switch point
        'End If
    Next i
    Dim oComplexString As ComplexStringElement
    Set oComplexString = CreateComplexStringElement1(lineElements)
    
    'Place on active model
    oComplexString.Redraw msdDrawingModeNormal
    ActiveModelReference.AddElement oComplexString
    
    Debug.Print "Elements in chain: " & numElements
    'Do I need to delete the old elements? Will this break the complex string?
    'May have to get the elements with their ID to remove them
    For intI = 0 To numElements - 1
        ActiveModelReference.RemoveElement lineElements(intI)
    Next intI
    
    Set PlaceComplexString = oComplexString
End Function

Attribute VB_Name = "EditModule"
Function ConvertOldRoadLevel()
    Dim types As New Collection
    types.Add 17 ' Text Node
    types.Add 7  ' Text
    ConvertLevel "Old_Level_23", "Exist Roads EOP Text", types, Nothing
    ConvertLevel "Exist Roads EOP", "Exist Roads EOP Text", types, Nothing
End Function

Function RoadSoilToEOP()
    Dim ee As ElementEnumerator
    Dim oScanCriteria As ElementScanCriteria
    Set oScanCriteria = New ElementScanCriteria
    oScanCriteria.ExcludeAllLevels
    oScanCriteria.IncludeLevel ActiveModelReference.Levels("Exist Roads Soil")
    oScanCriteria.ExcludeAllTypes
    oScanCriteria.IncludeType msdElementTypeText
    Set ee = ActiveModelReference.Scan(oScanCriteria)
    Dim oElem As TextElement
    Dim subElements As ElementEnumerator
    While ee.MoveNext
        Set oElem = ee.Current
        If oElem.text = "BST" Or oElem.text = "SOIL" Or oElem.text = "CONC" Or oElem.text = "GRAVEL" Then
        
        Else
            oElem.Level = ActiveModelReference.Levels("Exist Roads EOP Text")
            oElem.Rewrite
                oElem.Redraw
        End If
    Wend
End Function

Function ConvertMapText()
    Dim ee As ElementEnumerator
    Dim oScanCriteria As ElementScanCriteria
    Set oScanCriteria = New ElementScanCriteria
    oScanCriteria.ExcludeAllLevels
    oScanCriteria.IncludeLevel ActiveModelReference.Levels("Level 63")
    oScanCriteria.ExcludeAllTypes
    oScanCriteria.IncludeType msdElementTypeText
    Set ee = ActiveModelReference.Scan(oScanCriteria)
    Dim oElem As TextElement
    Dim subElements As ElementEnumerator
    While ee.MoveNext
        Set oElem = ee.Current
        If Left(oElem.text, 3) = "MAP" Then
            Set oElem.Level = ActiveModelReference.Levels("Level 62")
            If Left(oElem.text, 4) = "MAP " Then
                oElem.text = "MAP-" & Right(oElem.text, Len(oElem.text) - 4)
            End If
            oElem.Rewrite
            oElem.Redraw
        End If
    Wend
End Function

Function ConvertOldAddressesLevel()
    Dim types As New Collection
    types.Add 17
    types.Add 7
    ConvertLevel AutoBoreForm.OldAddressLevel, "Exist Building Text", types, Nothing
End Function

Function ConvertBoreTextNode()
    Dim ee As ElementEnumerator
    Dim oScanCriteria As ElementScanCriteria
    Set oScanCriteria = New ElementScanCriteria
    oScanCriteria.ExcludeAllLevels
    oScanCriteria.IncludeLevel ActiveModelReference.Levels("CATV Line UBO Text")
    oScanCriteria.ExcludeAllTypes
    oScanCriteria.IncludeType msdElementTypeTextNode
    Set ee = ActiveModelReference.Scan(oScanCriteria)
    Dim oElem As TextNodeElement
    Dim subElements As ElementEnumerator
    While ee.MoveNext
        Set oElem = ee.Current
        ' Check if it is a bore label
        If oElem.TextLine(1) = "DIRECTIONAL BORE" Then
            'Check if element already has the text
            If InStr(oElem.TextLine(3), "BORE HOLE") = 0 Then
                oElem.TextLine(3) = "3"" BORE HOLE FOR 1-2"" CONDUIT AT A"
                oElem.Color = 87
                oElem.Rewrite
                oElem.Redraw
            End If
        End If
    Wend
End Function

Function ConvertLevel(oldLevelName As String, newLevelName As String, types As Collection, template As Element)
    Dim ee As ElementEnumerator
    Dim oScanCriteria As ElementScanCriteria
    Dim newLevel As Level
    Set newLevel = ActiveDesignFile.Levels.Find(newLevelName)
    Dim TextSize As Double
    TextSize = CDbl(AutoBoreForm.TextSize)
    If newLevel Is Nothing Then
        'No new level
        MsgBox "New level does not exist!"
        Exit Function
    End If
    If template Is Nothing Then
        Set oScanCriteria = New ElementScanCriteria
        oScanCriteria.ExcludeAllLevels
        oScanCriteria.IncludeLevel newLevel
        Set ee = ActiveModelReference.Scan(oScanCriteria)
        If ee.MoveNext Then Set template = ee.Current
    End If
    Set oScanCriteria = New ElementScanCriteria
    Dim oldLevel As Level
    Set oldLevel = ActiveModelReference.Levels.Find(oldLevelName)
    If oldLevel Is Nothing Then
        'No old level
        MsgBox "No old level found"
        Exit Function
    End If
    oScanCriteria.ExcludeAllLevels
    oScanCriteria.IncludeLevel oldLevel
    If types.count <> 0 Then
        oScanCriteria.ExcludeAllTypes
        For i = 1 To types.count
            oScanCriteria.IncludeType types.item(i)
        Next i
    End If
    
    Dim oElem As Element
    Set ee = ActiveModelReference.Scan(oScanCriteria)
    While ee.MoveNext
        Set oElem = ee.Current
        oElem.Level = newLevel
        If Not template Is Nothing Then
            oElem.Color = template.Color
            oElem.LineStyle = template.LineStyle
            oElem.LineWeight = template.LineWeight
        End If
        oElem.Redraw msdDrawingModeNormal
        oElem.Rewrite
        Dim heightChange As Double
        If oElem.IsTextElement Then
            ' Change scale
            heightChange = TextSize / oElem.AsTextElement.TextStyle.height
            oElem.AsTextElement.ScaleUniform oElem.AsTextElement.origin, heightChange
        ElseIf oElem.IsTextNodeElement Then
            Dim textEnumerator As ElementEnumerator
            Set textEnumerator = oElem.AsTextNodeElement.GetSubElements
            If textEnumerator.MoveNext Then
                heightChange = TextSize / textEnumerator.Current.AsTextElement.TextStyle.height
                oElem.AsTextNodeElement.ScaleUniform oElem.AsTextNodeElement.origin, heightChange
            End If
            
            
        End If
        oElem.Redraw msdDrawingModeNormal
        oElem.Rewrite
    Wend
    
End Function


'<===> BORE PIT -> HAND HOLE <===>
'Have user select a bore pit to change to a hand hole
'Paste in hand hole element with the same orientation has bore pit & delete old bore pit
'Search for right away & align edge
'Hand hole length = 5.7250'
'Break lines half that distance on both sides
'Search for bore text on side of R/W
'Replace text with hand hole text

'Also change line from plow to bore along

Function ChangeBoreHandHole()
    Debug.Print "Swapping Element"
    'Get starting element from selection
    If Not ActiveModelReference.AnyElementsSelected Then
        MsgBox "The macro requires a selection set"
        Exit Function
    End If
    Dim ee As ElementEnumerator
    Set ee = ActiveModelReference.GetSelectedElements 'Selected elements
    ee.Reset
    ee.MoveNext 'Move to the first element
    'Check if it is a line
    If ee.Current.IsComplexShapeElement Then
        'Bore to hand hole
        Debug.Print "Bore Pit to HH"
        BorePitToHandHole ee.Current.AsComplexShapeElement
    ElseIf ee.Current.IsCellElement Then
        'Hand hole to bore
        Debug.Print "HH to Bore Pit"
        HandHoleToBorePit ee.Current.AsCellElement
    ElseIf ee.Current.IsComplexStringElement Then
        'Bore Line
        Debug.Print "Bore Line"
        If Not ee.Current.Level Is Nothing Then
            If ee.Current.Level.name = "Level 30" Then
                'Confirmed bore line
                ChangeBoreLine ee.Current
            Else
                MsgBox "Selected line is not a bore line. Level: " & ee.Current.Level.name
            End If
        Else
            MsgBox "Selected line doesn't have a level"
        End If
    Else
        MsgBox "The macro requires a cell, complex shape, or complex string element " & ee.Current.Type
    End If
End Function

Function ChangeBoreLine(boreLine As Element)
    Debug.Print "Line Style: " & boreLine.LineStyle.name
    Dim roadName As String
    Dim centerPt As Point3d
    centerPt = boreLine.AsChainableElement.PointAtDistance(boreLine.AsChainableElement.length / 2)
    roadName = deleteNearbyDimensions(centerPt)
    If isBore(boreLine) Then
        'bore -> plow
        boreLine.LineStyle = ActiveDesignFile.LineStyles("2")
    Else
        'plow -> bore
        boreLine.LineStyle = ActiveDesignFile.LineStyles("0")
    End If
    boreLine.Rewrite
    ReDimensionBoreLine boreLine, roadName
End Function

Function HandHoleToBorePit(hh As CellElement)
    Dim originpt As Point3d
    originpt = hh.origin
    'Get nearest bore line
    Dim boreLines As Collection
    Set boreLines = GetTouchingBoreLines(originpt)
    If boreLines.count = 0 Then
        'No Bore Line Found
        MsgBox "No Bore Line Found touching the Hand Hole!"
        Exit Function
    End If
    
    Dim boreLine As Element
    Dim midpoint As Point3d
    Dim x As Double
    Dim y As Double
    x = 0
    y = 0
    'Find midpoint
    For i = 1 To boreLines.count
        Set boreLine = boreLines.item(i)
        If Point3dDistance(originpt, boreLine.AsChainableElement.startPoint) < 5 Then
            x = x + boreLine.AsChainableElement.startPoint.x
            y = y + boreLine.AsChainableElement.startPoint.y
        Else
            x = x + boreLine.AsChainableElement.endPoint.x
            y = y + boreLine.AsChainableElement.endPoint.y
        End If
    Next i
    midpoint = Point3dFromXY(x / boreLines.count, y / boreLines.count)
    
    Dim tempList As New Collection
    'Extend Bore Lines
    For i = 1 To boreLines.count
        Set boreLine = boreLines.item(i)
        Dim newLine As ComplexStringElement
        If Point3dDistance(originpt, boreLine.AsChainableElement.startPoint) < 5 Then
            Set newLine = ExtendLine(boreLine.AsComplexStringElement, midpoint, True)
        Else
            Set newLine = ExtendLine(boreLine.AsComplexStringElement, midpoint, False)
        End If
        tempList.Add newLine
    Next i

    
    Set boreLines = GetTouchingBoreLines(originpt)
    If boreLines.count = 0 Then
        'No Bore Line Found
        Debug.Print "Couldn't find new lines"
        For i = 1 To tempList.count
            boreLines.Add tempList.item(i)
        Next i
    End If
    
    Set boreLine = boreLines.item(1)
    
    'Get a a couple points on the line
    Dim closestPos As Point3d
    Dim edge As Point3d
    closestPos = boreLine.AsIntersectableElement.ProjectPointOnPerpendicular(originpt, Matrix3dIdentity)
    Dim distance As Double
    distance = boreLine.AsChainableElement.DistanceAtPoint(closestPos)
    If distance + 2.3 > boreLine.AsChainableElement.length Then
        edge = boreLine.AsChainableElement.PointAtDistance(distance - 2.3)
    Else
        edge = boreLine.AsChainableElement.PointAtDistance(distance + 2.3)
    End If
    
    'Delete old hand hole
    ActiveModelReference.RemoveElement hh
    'Search for old label to delete
    Dim nearby As Collection
    Set nearby = Utils.NearbyElements(originpt, 30)
    Dim oElem As Element
    For i = 1 To nearby.count
        Set oElem = nearby.item(i)
        If oElem.IsTextNodeElement Then
            If InStr(oElem.AsTextNodeElement.TextLine(1), "BORE PIT:") <> 0 Then
                ActiveModelReference.RemoveElement oElem
            End If
        End If
    Next i
    
    'Add Bore Pit
    AutoBoreModule.PlaceBorePit closestPos, edge
    
    'Iterate through all touching bore lines
    Dim centerPt As Point3d
    Dim prevRoadName As String
    For i = 1 To boreLines.count
        Set boreLine = boreLines.item(i)
        'Delete old dimension and grab road name
        centerPt = boreLine.AsChainableElement.PointAtDistance(boreLine.AsChainableElement.length / 2)
        prevRoadName = deleteNearbyDimensions(centerPt)
        
        'Redimension line
        ReDimensionBoreLine boreLine, prevRoadName
    Next i
    'Undefine fence
    ActiveDesignFile.Fence.Undefine
End Function

Function BorePitToHandHole(pit As ComplexShapeElement)
    Dim originpt As Point3d
    originpt = pit.Centroid
    'Get nearest bore line
    Dim boreLines As Collection
    Set boreLines = GetTouchingBoreLines(originpt)
    If boreLines.count = 0 Then
        'No Bore Line Found
        MsgBox "No Bore Line Found touching the bore pit!"
        Exit Function
    End If
    
    Dim boreLine As Element
    Set boreLine = boreLines.item(1)
    
    'Get a a couple points on the line
    Dim closestPos As Point3d
    Dim edge As Point3d
    closestPos = boreLine.AsIntersectableElement.ProjectPointOnPerpendicular(originpt, Matrix3dIdentity)
    Dim distance As Double
    distance = boreLine.AsChainableElement.DistanceAtPoint(closestPos)
    If distance + 2.3 > boreLine.AsChainableElement.length Then
        edge = boreLine.AsChainableElement.PointAtDistance(distance - 2.3)
    Else
        edge = boreLine.AsChainableElement.PointAtDistance(distance + 2.3)
    End If
    
    'Delete old pit
    ActiveModelReference.RemoveElement pit
    'Search for old label to delete
    Dim nearby As Collection
    Set nearby = Utils.NearbyElements(originpt, 30)
    Dim oElem As Element
    For i = 1 To nearby.count
        Set oElem = nearby.item(i)
        If oElem.IsTextNodeElement Then
            If InStr(oElem.AsTextNodeElement.TextLine(1), "BORE PIT:") <> 0 Then
                ActiveModelReference.RemoveElement oElem
            End If
        End If
    Next i
    
    'Add Hand Hole
    AutoBoreModule.PlaceHandHole closestPos, edge
    'Iterate through all touching bore lines
    
    Dim breakPt As Point3d
    Dim centerDistance As Double
    Dim centerPt As Point3d
    Dim prevRoadName As String
    Dim e1 As Element
    Dim e2 As Element
    For i = 1 To boreLines.count
        Set boreLine = boreLines.item(i)
        'Delete old dimension and grab road name
        centerPt = boreLine.AsChainableElement.PointAtDistance(boreLine.AsChainableElement.length / 2)
        prevRoadName = deleteNearbyDimensions(centerPt)
        'Break if an endpoint is within 3 ft from originpt
        closestPos = boreLine.AsIntersectableElement.ProjectPointOnPerpendicular(closestPos, Matrix3dIdentity)
        centerDistance = boreLine.AsChainableElement.DistanceAtPoint(closestPos)
        If Point3dDistance(boreLine.AsChainableElement.startPoint, originpt) < 3 Then
            breakPt = boreLine.AsChainableElement.PointAtDistance(centerDistance + (5.725 / 2))
            boreLine.PartialDelete e1, e2, boreLine.AsChainableElement.startPoint, breakPt, closestPos, 1
        ElseIf Point3dDistance(boreLine.AsChainableElement.endPoint, originpt) < 3 Then
            breakPt = boreLine.AsChainableElement.PointAtDistance(centerDistance - (5.725 / 2))
            boreLine.PartialDelete e1, e2, boreLine.AsChainableElement.endPoint, breakPt, closestPos, 1
        End If
        'Redimension line
        ActiveModelReference.RemoveElement boreLine
        If Not e1 Is Nothing Then
            ActiveModelReference.AddElement e1
            e1.Redraw
            ReDimensionBoreLine e1, prevRoadName
        End If
        If Not e2 Is Nothing Then
            ActiveModelReference.AddElement e2
            e2.Redraw
            ReDimensionBoreLine e2, prevRoadName
        End If
    Next i
    'Undefine fence
    ActiveDesignFile.Fence.Undefine
End Function

'Auto move bore text out of intersecting elements
'Scan model for Level 30 text nodes
'Check for elements within 20 feet
'Locate empty space
'Move
'Scan model for CATV Line UBO Text as text node element
'Check for elements within 70 feet
'Locate empty space w/ line of sight
'Move
'Draw line 35 feet from space to the original spot

Function RelocateLabels()

End Function

'Searches in a circle around origin to find an open space
'Will not find space on other side of R/W
'lineOfSight controls whether the new space must have a line of sight to the previous space (minus requiredRadius feet from line)
Function LocateSpace(origin As Point3d, requiredRadius As Double, lineOfSight As Boolean) As Point3d
    
End Function

Function RemovePit()
    Debug.Print "Removing Bore Pit / Hand Hole"
    'Get starting element from selection
    If Not ActiveModelReference.AnyElementsSelected Then
        MsgBox "The macro requires a selection set"
        Exit Function
    End If
    Dim ee As ElementEnumerator
    Set ee = ActiveModelReference.GetSelectedElements 'Selected elements
    ee.Reset
    ee.MoveNext 'Move to the first element
    'Check if it is a pit or hand hole
    Dim oElem As Element
    Dim pit As Boolean
    Set oElem = ee.Current
    Dim originpt As Point3d
    If oElem.IsComplexShapeElement Then
        'Bore Pit
        pit = True
        originpt = oElem.AsComplexShapeElement.Centroid
    ElseIf oElem.IsCellElement Then
        'Hand hole
        pit = False
        originpt = oElem.AsCellElement.origin
    Else
        MsgBox "The macro requires a cell or complex shape element " & ee.Current.Type
        Exit Function
    End If
    
    'Delete old pit
    ActiveModelReference.RemoveElement oElem
    'Search for old label to delete
    Dim nearby As Collection
    Set nearby = Utils.NearbyElements(originpt, 30)
    Dim oElement As Element
    For i = 1 To nearby.count
        Set oElement = nearby.item(i)
        If oElement.IsTextNodeElement Then
            If InStr(oElement.AsTextNodeElement.TextLine(1), "BORE PIT:") <> 0 Then
                ActiveModelReference.RemoveElement oElement
            End If
        End If
    Next i
    
    Dim roadName As String
    Dim centerPt As Point3d
    Dim uncombinedLines As New Collection
    'Get nearest bore line
        Dim boreLines As Collection
        Set boreLines = GetTouchingBoreLines(originpt)
        If boreLines.count = 0 Then
            'No Bore Line Found
            MsgBox "No Bore Line Found touching the element!"
            Exit Function
        End If
        
        Dim boreLine As Element
    If Not pit Then
        'Extend bore lines for hand hole
        
        Dim midpoint As Point3d
        Dim x As Double
        Dim y As Double
        x = 0
        y = 0
        'Find midpoint
        For i = 1 To boreLines.count
            Set boreLine = boreLines.item(i)
            If Point3dDistance(originpt, boreLine.AsChainableElement.startPoint) < 5 Then
                x = x + boreLine.AsChainableElement.startPoint.x
                y = y + boreLine.AsChainableElement.startPoint.y
            Else
                x = x + boreLine.AsChainableElement.endPoint.x
                y = y + boreLine.AsChainableElement.endPoint.y
            End If
        Next i
        midpoint = Point3dFromXY(x / boreLines.count, y / boreLines.count)
        
        'Extend Bore Lines and undimension
        
        For i = 1 To boreLines.count
            Set boreLine = boreLines.item(i)
            centerPt = boreLine.AsChainableElement.PointAtDistance(boreLine.AsChainableElement.length / 2)
            roadName = deleteNearbyDimensions(centerPt)
            Dim newLine As ComplexStringElement
            If Point3dDistance(originpt, boreLine.AsChainableElement.startPoint) < 5 Then
                Set newLine = ExtendLine(boreLine.AsComplexStringElement, midpoint, True)
            Else
                Set newLine = ExtendLine(boreLine.AsComplexStringElement, midpoint, False)
            End If
            uncombinedLines.Add newLine
        Next i
    Else
        For i = 1 To boreLines.count
            Set boreLine = boreLines.item(i)
            centerPt = boreLine.AsChainableElement.PointAtDistance(boreLine.AsChainableElement.length / 2)
            roadName = deleteNearbyDimensions(centerPt)
            uncombinedLines.Add boreLine
        Next i
    End If
    
    If uncombinedLines.count > 1 Then
        Dim combinedLine As ComplexStringElement
        On Error Resume Next
        Set combinedLine = combineComplexStrings(uncombinedLines.item(1), uncombinedLines.item(2))
        ReDimensionBoreLine combinedLine, roadName
    End If
    
    'Undefine fence
    ActiveDesignFile.Fence.Undefine
End Function

'Adds a bore pit or hand hole to the line
'Paste in the element you want at your desired location
'Select the element and run the program
'Element will be auto-rotated and positioned to the nearest line
'Surrounding lines will be re-dimensioned
Function AddPit()
    Debug.Print "Adding Bore Pit / Hand Hole"
    'Get starting element from selection
    If Not ActiveModelReference.AnyElementsSelected Then
        MsgBox "The macro requires a selection set"
        Exit Function
    End If
    Dim ee As ElementEnumerator
    Set ee = ActiveModelReference.GetSelectedElements 'Selected elements
    ee.Reset
    ee.MoveNext 'Move to the first element
    'Check if it is a pit or hand hole
    Dim oElem As Element
    Dim pit As Boolean
    Set oElem = ee.Current
    Dim originpt As Point3d
    If oElem.IsComplexShapeElement Then
        'Bore Pit
        pit = True
        originpt = oElem.AsComplexShapeElement.Centroid
    ElseIf oElem.IsCellElement Then
        'Hand hole
        pit = False
        originpt = oElem.AsCellElement.origin
    Else
        MsgBox "The macro requires a cell or complex shape element " & ee.Current.Type
        Exit Function
    End If
    
    Dim boreLine As Element
    Set boreLine = GetNearestBoreLine(originpt)
    
    If boreLine Is Nothing Then
        'No Bore Line Found
        MsgBox "No Bore Line Found within Maximum R/W Distance"
        Exit Function
    End If
    
    Dim closestPos As Point3d
    Dim edge As Point3d
    closestPos = boreLine.AsIntersectableElement.ProjectPointOnPerpendicular(originpt, Matrix3dIdentity)
    edge = boreLine.AsChainableElement.PointAtDistance(boreLine.AsChainableElement.DistanceAtPoint(closestPos) + 2.3)
    
    ActiveModelReference.RemoveElement oElem
    
    'Delete old dimensions
    Dim centerPt As Point3d
    centerPt = boreLine.AsChainableElement.PointAtDistance(boreLine.AsChainableElement.length / 2)
    Dim prevRoadName As String
    prevRoadName = deleteNearbyDimensions(centerPt)
    
    
    'Place new elements
    Dim e1 As Element
    Dim e2 As Element
    If pit Then
        AutoBoreModule.PlaceBorePit closestPos, edge
        'Break element at center of bore pit
        boreLine.PartialDelete e1, e2, closestPos, closestPos, closestPos, 1
    Else
        AutoBoreModule.PlaceHandHole closestPos, edge
        'Break element 5.725 ft
        Dim beforePt As Point3d
        Dim afterPt As Point3d
        Dim centerDistance As Double
        centerDistance = boreLine.AsChainableElement.DistanceAtPoint(closestPos)
        beforePt = boreLine.AsChainableElement.PointAtDistance(centerDistance - (5.725 / 2))
        afterPt = boreLine.AsChainableElement.PointAtDistance(centerDistance + (5.725 / 2))
        boreLine.PartialDelete e1, e2, beforePt, afterPt, closestPos, 1
    End If
    'Replace boreLine & redimention
    ActiveModelReference.RemoveElement boreLine
    If Not e1 Is Nothing Then
        ActiveModelReference.AddElement e1
        e1.Redraw
        ReDimensionBoreLine e1, prevRoadName
    End If
    If Not e2 Is Nothing Then
        ActiveModelReference.AddElement e2
        e2.Redraw
        ReDimensionBoreLine e2, prevRoadName
    End If
    'Undefine fence
    ActiveDesignFile.Fence.Undefine
End Function

'Deletes Text Node Elements with level CATV Line UBO Text
'Returns The road name in the dimension
Function deleteNearbyDimensions(center As Point3d) As String
    Dim nearby As Collection
    Set nearby = Utils.NearbyElements(center, 5)
    Dim oElem As Element
    Dim name As String
    name = "???"
    Dim subString() As String
    For i = 1 To nearby.count
        Set oElem = nearby.item(i)
        If oElem.IsTextNodeElement And Not oElem.Level Is Nothing Then
            If oElem.Level.name = "CATV Line UBO Text" Then
                'Dimension
                'Get the road name
                name = oElem.AsTextNodeElement.TextLine(2)
                subString = Split(name, " ")
                'Take the right road name of the 2nd line
                'Total line length - length of the 3 starting strings ex: "40 FEET ALONG NC-73" - +3 is added for the 3 spaces
                name = Right(name, Len(name) - (Len(subString(0)) + Len(subString(1)) + Len(subString(2)) + 3))

                ActiveModelReference.RemoveElement oElem
            End If
        End If
    Next i
    deleteNearbyDimensions = name
End Function


'Returns the nearest bore line
Function GetNearestBoreLine(startPos As Point3d) As Element
    'Get nearby elements
    Dim rwSize As Double
    rwSize = CDbl(AutoBoreForm.MaxRWDistance)
    Dim nearby As Collection
    Set nearby = Utils.NearbyElements(startPos, rwSize)
    Dim oElem As Element
    Dim closestPos As Point3d
    closestPos = Point3dFromXY(0, 0)
    Dim closestEle As Element
    
    'Iterate through nearby elements
    For i = 1 To nearby.count
        Set oElem = nearby.item(i)
        If oElem.IsGraphical Then
            If oElem.IsChainableElement And oElem.IsIntersectableElement Then
                If Not oElem.Level Is Nothing Then
                    If oElem.Level.name = "Level 30" Then
                        'Intersectable level 30 line = bore line
                        Dim currentPos As Point3d
                        currentPos = oElem.AsIntersectableElement.ProjectPointOnPerpendicular(startPos, Matrix3dIdentity)
                        If Point3dDistance(currentPos, startPos) < Point3dDistance(closestPos, startPos) Then
                            'currentPos is closer than previous
                            closestPos = currentPos
                            Set closestEle = oElem
                        End If
                    End If
                End If
            End If
        End If
    Next i
    Set GetNearestBoreLine = closestEle
End Function

'Returns bore lines that are within 5 ft of the start Pos
Function GetTouchingBoreLines(startPos As Point3d) As Collection
    'Get nearby elements
    Dim nearby As Collection
    Set nearby = Utils.NearbyElements(startPos, 5)
    Dim oElem As Element
    Dim lines As New Collection
    
    'Iterate through nearby elements
    For i = 1 To nearby.count
        Set oElem = nearby.item(i)
        If oElem.IsGraphical Then
            If oElem.IsChainableElement And oElem.IsIntersectableElement Then
                If Not oElem.Level Is Nothing Then
                    If oElem.Level.name = "Level 30" Then
                        'Intersectable level 30 line = bore line
                        lines.Add oElem
                    End If
                End If
            End If
        End If
    Next i
    Set GetTouchingBoreLines = lines
End Function


'Redimension line & get connected of same type
'Check for bore pits/HH
Function ReDimensionBoreLine(boreLine As Element, roadName As String)
    If Not (boreLine.IsIntersectableElement And boreLine.IsChainableElement) Then
        Debug.Print "Not intersectable or chainable"
        Exit Function
    End If
    Dim centerPt As Point3d
    centerPt = boreLine.AsChainableElement.PointAtDistance(boreLine.AsChainableElement.length / 2)
    Dim dimension As Double
    dimension = boreLine.AsChainableElement.length
    'Add stuff on for end points
    dimension = dimension + GetNearbyPitDimensionAddition(boreLine.AsChainableElement.endPoint)
    dimension = dimension + GetNearbyPitDimensionAddition(boreLine.AsChainableElement.startPoint)
    Dim dimensionString As String
    dimensionString = CStr(Int((dimension + 5) / 5) * 5)
    If roadName = "???" Then
        'Try to find a nearby road
        roadName = AutoBoreModule.GetNearestRoad(boreLine.AsChainableElement.length / 2, AutoBoreModule.getRoadNames(boreLine, 1000))
    End If
    Dim label As TextNodeElement
    If isBore(boreLine) Then
        'bore
        Set label = Utils.CreateBoreDimension(centerPt, dimensionString, roadName, 1)
    Else
        'plow
        Set label = Utils.CreateBoreDimension(centerPt, dimensionString, roadName, 0)
    End If
    ActiveModelReference.AddElement label
    label.Redraw
End Function

Function isBore(boreLine As Element) As Boolean
    If boreLine.IsComplexElement Then
    
    Dim ee As ElementEnumerator
    Set ee = boreLine.AsComplexElement.GetSubElements
    ee.MoveNext
    isBore = ee.Current.LineStyle.number = 0
    Else
    isBore = boreLine.LineStyle.number = 0
    End If
    
End Function

'Returns (4.656 / 2) if there is a nearby bore pit
'Returns (5.725 / 2) if there is a nearby hand hole
'Returns 0 otherwise
Function GetNearbyPitDimensionAddition(searchPt As Point3d) As Double
    Dim dimension As Double
    dimension = 0
    'Search for nearby bore pits and hand holes
    Dim oElem As Element
    Dim nearby As Collection
    Set nearby = Utils.NearbyElements(searchPt, 1)
    For i = 1 To nearby.count
        Set oElem = nearby.item(i)
        If IsBorePit(oElem) Then
                'Bore Pit
                dimension = 4.656
                Exit For
        ElseIf oElem.IsCellElement Then
            If oElem.AsCellElement.name = "EXIST UTILITIES TELEPHONE HAND HOLE" Then
                'Hand Hole
                dimension = 5.725
                Exit For
            End If
        End If
    Next i
    GetNearbyPitDimensionAddition = dimension
End Function

'Extends a complex string from the start or end
Function ExtendLine(original As ComplexStringElement, extendPt As Point3d, start As Boolean) As ComplexStringElement
    ActiveSettings.Level = original.Level
    ActiveSettings.LineWeight = original.LineWeight
    ActiveSettings.Color = original.Color
    ActiveSettings.LineStyle = original.LineStyle
    Dim replacement As ComplexStringElement
    Dim verticies(0 To 1) As Point3d
    Dim newLine As LineElement
    Dim components() As ChainableElement
    Dim numComponents As Integer
    numComponents = 0
    Dim ee As ElementEnumerator
    Set ee = original.GetSubElements
    While ee.MoveNext
        numComponents = numComponents + 1
    Wend
    
    ReDim components(numComponents + 1)

    If start Then
        'Extend start
        verticies(0) = extendPt
        verticies(1) = original.startPoint
        
        Set newLine = CreateLineElement1(original, verticies)
        
        ee.Reset
        Set components(0) = newLine
        For i = 1 To numComponents
            ee.MoveNext
            Set components(i) = ee.Current
        Next i
        
    Else
        'Extend end
        verticies(0) = original.endPoint
        verticies(1) = extendPt
        
        Set newLine = CreateLineElement1(original, verticies)
        
        ee.Reset
        
        For i = 0 To numComponents - 1
            ee.MoveNext
            Set components(i) = ee.Current
        Next i
        Set components(numComponents) = newLine
    End If
    
    Set replacement = CreateComplexStringElement1(components)
    ActiveModelReference.AddElement replacement
    replacement.Redraw msdDrawingModeNormal
    ActiveModelReference.RemoveElement original
    
    Set ExtendLine = replacement
End Function

'Combine 2 bore lines into 1
Function combineComplexStrings(line1 As ComplexStringElement, line2 As ComplexStringElement) As ComplexStringElement
    ActiveSettings.Level = line1.Level
    ActiveSettings.LineWeight = line1.LineWeight
    ActiveSettings.Color = line1.Color
    'Longer one overrides line style
    Dim ls As LineStyle
    
    If line1.length > line2.length Then
        If isBore(line1) Then
            Set ls = ActiveDesignFile.LineStyles("0")
        Else
            Set ls = ActiveDesignFile.LineStyles("2")
        End If
    Else
        If isBore(line2) Then
            Set ls = ActiveDesignFile.LineStyles("0")
        Else
            Set ls = ActiveDesignFile.LineStyles("2")
        End If
    End If

    If Point3dDistance(line1.endPoint, line2.startPoint) > 1 And Point3dDistance(line1.startPoint, line2.endPoint) > 1 Then
        'lines are facing eachother - reverse
        line1.Reverse
    End If
    Dim ordered As Boolean
    ordered = Point3dDistance(line1.endPoint, line2.startPoint) < 1
    Dim ee1 As ElementEnumerator
    Dim ee2 As ElementEnumerator
    Dim numEle1 As Integer
    Dim numEle2 As Integer
    numEle1 = 0
    numEle2 = 0
    Dim components() As ChainableElement
    Set ee1 = line1.GetSubElements
    While ee1.MoveNext
        numEle1 = numEle1 + 1
    Wend
    Set ee2 = line2.GetSubElements
    While ee2.MoveNext
        numEle2 = numEle2 + 1
    Wend
    ee1.Reset
    ee2.Reset
    ReDim components(numEle1 + numEle2)
    Dim oElem As Element
    If ordered Then
        For i = 0 To numEle1 - 1
            ee1.MoveNext
            Set oElem = ee1.Current
            Set oElem.LineStyle = ls
            oElem.Rewrite
            Set components(i) = oElem.AsChainableElement
        Next i
        For i = 0 To numEle2 - 1
            ee2.MoveNext
            Set oElem = ee2.Current
            Set oElem.LineStyle = ls
            oElem.Rewrite
            Set components(i + numEle1) = oElem.AsChainableElement
        Next i
    Else
        For i = 0 To numEle2 - 1
            ee2.MoveNext
            Set oElem = ee2.Current
            Set oElem.LineStyle = ls
            oElem.Rewrite
            Set components(i) = oElem.AsChainableElement
        Next i
        For i = 0 To numEle1 - 1
            ee1.MoveNext
            Set oElem = ee1.Current
            Set oElem.LineStyle = ls
            oElem.Rewrite
            Set components(i + numEle2) = oElem.AsChainableElement
        Next i
    End If
    
    Dim result As ComplexStringElement
    Set result = CreateComplexStringElement1(components)
    ActiveModelReference.RemoveElement line1
    ActiveModelReference.RemoveElement line2
    result.Redraw msdDrawingModeNormal
    ActiveModelReference.AddElement result
    Set combineComplexStrings = result
End Function

Function ConvertBoundaryShapes()
    Debug.Print "Converting Boundary Shapes"
    Dim prevLevel As Level
    Dim prevLineStyle As LineStyle
    Dim prevLineWeight As Long
    Dim prevLineColor As Long
    Dim prevDimensionStyle As DimensionStyle
    With ActiveSettings
        Set prevLevel = .Level
        Set prevLineStyle = .LineStyle
        prevLineWeight = .LineWeight
        prevLineColor = .Color
        Set prevDimensionStyle = .DimensionStyle
        Set .Level = ActiveModelReference.Levels("Level 63")
        Set .LineStyle = ByLevelLineStyle
        .Color = 1
        .LineWeight = 0
    End With
    Dim ee As ElementEnumerator
    Dim oScanCriteria As ElementScanCriteria
    Set oScanCriteria = New ElementScanCriteria
    'Scan for all map boundaries
    oScanCriteria.ExcludeAllTypes
    oScanCriteria.IncludeType msdElementTypeShape
    oScanCriteria.ExcludeAllColors
    oScanCriteria.IncludeColor CInt(AutoBoreForm.ShapeBoundaryColor)
    Set ee = ActiveModelReference.Scan(oScanCriteria)
    Dim shapeEle As ShapeElement
    Dim chainableElements() As ChainableElement
    Dim numElements As Integer
    Dim line As LineElement
    Dim newShape As ComplexShapeElement
    While ee.MoveNext
        If Not ee.Current.Level Is Nothing Then
            If ee.Current.Level.name = "Level 63" Or ee.Current.Level.name = AutoBoreForm.ConvertShapeLevel Then
                Debug.Print "Converting Shape"
                Set shapeEle = ee.Current
                If shapeEle.Level.name = AutoBoreForm.ConvertShapeLevel Then
                    shapeEle.Level = ActiveModelReference.Levels("Level 63")
                    shapeEle.Rewrite
                    shapeEle.Redraw
                End If
                numElements = shapeEle.VerticesCount - 1
                ReDim chainableElements(0 To numElements - 1)
                For i = 0 To numElements - 1
                    Set line = CreateLineElement2(shapeEle, shapeEle.Vertex(i + 1), shapeEle.Vertex(i + 2))
                    Set chainableElements(i) = line
                Next i
                ActiveModelReference.RemoveElement shapeEle
                Set newShape = CreateComplexShapeElement1(chainableElements)
                ActiveModelReference.AddElement newShape
                newShape.Redraw
                newShape.Rewrite
            End If
        End If
    Wend
    ' Return active settings
    With ActiveSettings
        Set .Level = prevLevel
        Set .LineStyle = prevLineStyle
        .LineWeight = prevLineWeight
        .Color = prevLineColor
        Set .DimensionStyle = prevDimensionStyle
    End With
End Function

Attribute VB_Name = "ElementProximity"
Option Explicit

' Returns a point on the line from origin to the element's center that is
' offsetDistance away from the element's range.
Function GetOffsetPointFromElementRange(origin As Point3d, elem As Element, offsetDistance As Double) As Point3d
    Dim elemRange As Range3d
    Dim center As Point3d
    Dim dir As Point3d
    Dim IntersectionPoint As Point3d
    Dim foundIntersection As Boolean
    Dim dirLen As Double
    Dim unitDir As Point3d
    
    On Error GoTo ErrorHandler
    
    ' Get the element's range
    elemRange = elem.Range
    
    ' Compute the center of the element's range
    center = Point3dFromXYZ((elemRange.low.x + elemRange.high.x) / 2#, _
                            (elemRange.low.y + elemRange.high.y) / 2#, _
                            (elemRange.low.Z + elemRange.high.Z) / 2#)

    ' Compute direction vector from origin to center
    dir = Point3dSubtract(center, origin)
    
    ' Find intersection of the line segment (origin->center) with the element's range box
    foundIntersection = IntersectLineWithRange(origin, dir, elemRange, IntersectionPoint)
    
    If Not foundIntersection Then
        ' If no intersection found, just return a point closer to center minus offsetDistance
        ' This scenario may happen if the origin is inside the box or no intersection is detected.
        ' For robustness, we handle it by simply returning the center shifted towards origin.
        
        ' Normalize direction and move center away by offsetDistance
        dirLen = Sqr(dir.x * dir.x + dir.y * dir.y + dir.Z * dir.Z)
        If dirLen > 0 Then
            unitDir = Point3dFromXYZ(dir.x / dirLen, dir.y / dirLen, dir.Z / dirLen)
            ' Move from center along -unitDir by offsetDistance
            GetOffsetPointFromElementRange = Point3dFromXYZ(center.x - unitDir.x * offsetDistance, _
                                                            center.y - unitDir.y * offsetDistance, _
                                                            center.Z - unitDir.Z * offsetDistance)
        Else
            ' If direction length is zero (origin == center), just return the center
            GetOffsetPointFromElementRange = center
        End If
        Exit Function
    End If
    
    ' If intersection found, we now move "offsetDistance" away from the box along the line
    ' The intersectionPoint is on or very close to the surface of the box.
    ' We'll backtrack along the line (origin->center) by offsetDistance.

    Dim intersectionDir As Point3d
    intersectionDir = Point3dSubtract(IntersectionPoint, origin)
    
    Dim intersectionDist As Double
    intersectionDist = Sqr(intersectionDir.x ^ 2 + intersectionDir.y ^ 2 + intersectionDir.Z ^ 2)
    
    ' If intersectionDist is > offsetDistance, we can safely move offsetDistance away along this line
    ' Normalize intersectionDir
    If intersectionDist > 0 Then
        Dim intersectionUnit As Point3d
        intersectionUnit = Point3dFromXYZ(intersectionDir.x / intersectionDist, intersectionDir.y / intersectionDist, intersectionDir.Z / intersectionDist)
        
        ' Move intersection point back by offsetDistance
        GetOffsetPointFromElementRange = Point3dFromXYZ(IntersectionPoint.x - intersectionUnit.x * offsetDistance, _
                                                        IntersectionPoint.y - intersectionUnit.y * offsetDistance, _
                                                        IntersectionPoint.Z - intersectionUnit.Z * offsetDistance)
    Else
        ' If intersectionDist is 0 (unlikely but possible if origin is on box surface),
        ' just return origin offset towards center by offsetDistance
        dirLen = Sqr(dir.x * dir.x + dir.y * dir.y + dir.Z * dir.Z)
        If dirLen > 0 Then
            unitDir = Point3dFromXYZ(dir.x / dirLen, dir.y / dirLen, dir.Z / dirLen)
            GetOffsetPointFromElementRange = Point3dFromXYZ(origin.x + unitDir.x * offsetDistance, _
                                                            origin.y + unitDir.y * offsetDistance, _
                                                            origin.Z + unitDir.Z * offsetDistance)
        Else
            ' If origin == center, just return origin for lack of a better solution
            GetOffsetPointFromElementRange = origin
        End If
    End If

    Exit Function

ErrorHandler:
    ' On error, just return the center for safety
    GetOffsetPointFromElementRange = center
End Function

' This function tries to find where a line (origin + t*dir, 0 <= t <= 1) intersects an axis-aligned box defined by elemRange.
' If an intersection is found between origin and origin+dir (assuming dir is from origin to center),
' it returns True and the intersection point.
Private Function IntersectLineWithRange(origin As Point3d, dir As Point3d, rng As Range3d, intersection As Point3d) As Boolean
    Dim tmin As Double, tmax As Double
    tmin = 0#
    tmax = 1#

    ' If any component of dir is 0, we must handle separately to avoid division by zero
    ' We'll use the "slab intersection" method for each axis
    If Not ClipLineAxis(origin.x, dir.x, rng.low.x, rng.high.x, tmin, tmax) Then Exit Function
    If Not ClipLineAxis(origin.y, dir.y, rng.low.y, rng.high.y, tmin, tmax) Then Exit Function
    If Not ClipLineAxis(origin.Z, dir.Z, rng.low.Z, rng.high.Z, tmin, tmax) Then Exit Function

    If tmax >= tmin And tmin >= 0 And tmin <= 1 Then
        intersection = Point3dFromXYZ(origin.x + dir.x * tmin, origin.y + dir.y * tmin, origin.Z + dir.Z * tmin)
        IntersectLineWithRange = True
    Else
        IntersectLineWithRange = False
    End If
End Function

' Helper function for axis-aligned clipping
Private Function ClipLineAxis(o As Double, d As Double, minVal As Double, maxVal As Double, ByRef tmin As Double, ByRef tmax As Double) As Boolean
    If Abs(d) < 0.000000000001 Then
        ' Line is parallel to this axis
        If o < minVal Or o > maxVal Then
            ClipLineAxis = False ' No intersection because line is outside slab
        Else
            ClipLineAxis = True ' Line stays within slab for this axis
        End If
    Else
        Dim t1 As Double, t2 As Double
        t1 = (minVal - o) / d
        t2 = (maxVal - o) / d
        ' Ensure t1 is the lower intersection
        If t1 > t2 Then
            Dim temp As Double
            temp = t1
            t1 = t2
            t2 = temp
        End If
        If t2 < tmin Or t1 > tmax Then
            ClipLineAxis = False
            Exit Function
        End If
        If t1 > tmin Then tmin = t1
        If t2 < tmax Then tmax = t2
        ClipLineAxis = True
    End If
End Function

Attribute VB_Name = "IntersectionList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private contents(999) As IntersectionPoint

Private list_size As Long

Property Get At(index As Long) As IntersectionPoint
    Set At = contents(index)
End Property

Public Function SetIntersectionType(index As Long, pType As String)
    If index < list_size Then contents(index).PointType = pType
End Function

Public Function SetIntersectionDistance(index As Long, distance As Double)
    If index < list_size Then contents(index).PointDistance = distance
End Function

' Get the an intersection point closest to a distance
'
' @param distance   The distance along the bore line to look for a bore line
' @param direcion   The direction in which to look for an intersection
' @param pType      The type of intersection to look for
' @returns          The closest intersection, or Nothing if none could be found with the parameters
Public Function GetIntersection(distance As Double, Optional direction As Integer = 0, Optional pType As String = "NONE", Optional entryType) As IntersectionPoint
    Dim closestIndex As Long
    closestIndex = SearchClosest(distance) ' get closest point to the distance
    
    ' Check if the point found is in the direction specified
    If direction > 0 And contents(closestIndex).PointDistance < distance Then
        closestIndex = closestIndex + 1
    ElseIf direction < 0 And contents(closestIndex).PointDistance > distance Then
        closestIndex = closestIndex - 1
    End If
    
    If closestIndex >= list_size - 1 Or closestIndex < 0 Then ' the last list element is the bore length, hence the -1
        ' Index out of bounds
        Set GetIntersection = Nothing
        Exit Function
    End If
    
    If pType = "NONE" Then
        ' No point type specified, return closest found
        Set GetIntersection = contents(closestIndex)
        Exit Function
    End If
    
    If direction = 0 Then direction = 1 ' Look forward for point type if no direction is specified
    
    Dim searchEntry As Boolean
    If IsMissing(entryType) Then
        searchEntry = True
    Else
        searchEntry = entryType
    End If
    
    Do While contents(closestIndex).PointType <> pType Or (Not IsMissing(entryType) And contents(closestIndex).EnterPoint <> searchEntry)
        closestIndex = closestIndex + direction
        If closestIndex < 0 Or closestIndex = list_size - 1 Then
            ' Out of bounds
            Set GetIntersection = Nothing
            Exit Function
        End If
    Loop
    
    Set GetIntersection = contents(closestIndex)
End Function

' Search for the index of the closest intersection
'
' @param distance   The distance along the bore line to find a nearby intersection at.
' @returns          The index of the closest intersection to the distance.
Public Function SearchClosest(distance As Double) As Long
    Dim high As Long
    Dim low As Long
    Dim mid As Long

    high = list_size - 1
    low = 0

    ' Binary search for closest index
    While low <= high
        mid = (low + high) \ 2
        If contents(mid).PointDistance < distance Then
            low = mid + 1
        ElseIf contents(mid).PointDistance > distance Then
            high = mid - 1
        Else
            SearchClosest = mid
            Exit Function
        End If
    Wend

    ' Choose the closest between low and high
    If low >= list_size Then
        SearchClosest = list_size - 1
    ElseIf high < 0 Then
        SearchClosest = 0
    ElseIf Abs(contents(low).PointDistance - distance) < Abs(contents(high).PointDistance - distance) Then
        SearchClosest = low
    Else
        SearchClosest = high
    End If
End Function

' Linearly search for a distance in the list. If you have a sorted list, use SearchClosest()
'
' @param distance       Distance along the bore line to search for.
' @param marginOfError  How far away a distance in the list has to be from the inputted distance to be returned.
' @returns              The index of the found distance, or -1 if the point doesn't exist
Function LinearSearch(distance As Double, marginOfError As Double, Optional pType As String = "NONE") As Long
    Dim i As Long
    For i = 0 To list_size - 1
        If Abs(contents(i).PointDistance - distance) < marginOfError Then
            If pType = "NONE" Or contents(i).PointType = pType Then
                LinearSearch = i
                Exit Function
            End If
        End If
    Next i
    LinearSearch = -1
End Function

' Check if a location is between intersections that can have an entry and exit point (e.g. soil)
'
' @param distance   The distance along the bore line that should be checked.
' @param pType      The type of point to look for.
Public Function IsBetweenIntersections(distance As Double, pType As String) As Boolean
    Dim point As IntersectionPoint
    Set point = GetIntersection(distance, 1, pType)
    If point Is Nothing Then
        IsBetweenIntersections = False
        Exit Function
    End If
    
    If Not point.EnterPoint Then
        ' The next intersection of pType is an exit point, so that means the previous intersection of pType should be an enter point which is before distance
        IsBetweenIntersections = True
        Exit Function
    End If
    
    IsBetweenIntersections = False
End Function

' Get the relative distance between intersections surrounding the point. The intended use case for this is to check if a guardrail and bridge on either side of the
' intersection point is less than a max distance which means that there is probably a guardrail where the distance is at. This functioon returns the distance between
' the bridge and the guardrail origin.
'
' @param distance       The distance along the bore line to get the point around
' @param pType1         The first point type to look for
' @param pType2         The second point type to look for
' @returns              The shortest length between the 2 point types that goes through the distance point. If the point types don't exist around the distance, then -1 is returned.
Public Function GetIntersectionDistance(distance As Double, pType1 As String, pType2 As String) As Double
    Dim minLength As Double
    minLength = -1
    Dim pointAfter As IntersectionPoint
    Dim pointBefore As IntersectionPoint
    Set pointAfter = GetIntersection(distance, 1, pType1)
    Set pointBefore = GetIntersection(distance, -1, pType2)
    If Not pointAfter Is Nothing And Not pointBefore Is Nothing Then
        minLength = pointAfter.PointDistance - pointBefore.PointDistance
    End If
    ' Switch the point type sides and check again
    Set pointAfter = GetIntersection(distance, 1, pType2)
    Set pointBefore = GetIntersection(distance, -1, pType1)
    If Not pointAfter Is Nothing And Not pointBefore Is Nothing Then
        If minLength = -1 Or pointAfter.PointDistance - pointBefore.PointDistance < minLength Then
            minLength = pointAfter.PointDistance - pointBefore.PointDistance
        End If
    End If
    GetIntersectionDistance = minLength
End Function

Public Sub SortList()
    Arrays.QuickIntersectionSort contents, 0, list_size - 1
End Sub


Public Sub Add(item As IntersectionPoint, Optional index As Long = -1)
    'Make sure index is in bounds
    If index < 0 Or index > list_size Then
        index = list_size
    End If
    'Change array size
    'ReDim contents(list_size + 1)
    If index = list_size Then
        Set contents(index) = item
    Else
        'Push everything back
        Dim tempVal As IntersectionPoint
        Dim tempVal2 As IntersectionPoint
        Set tempVal = contents(index)
        Set contents(index) = item
        For i = index + 1 To list_size - 1
            Set tempVal2 = contents(i)
            Set contents(i) = tempVal
            Set tempVal = tempVal2
        Next i
        Set contents(list_size) = tempVal
    End If
    list_size = list_size + 1
End Sub

Property Get ToArray() As Variant
    ToArray = contents
End Property

Public Sub PrintPoints()
    For i = 0 To list_size - 1
        Debug.Print i & ": " & contents(i).PointDistance & " = " & contents(i).PointType
    Next i
End Sub

Public Sub Remove(index As Long)
    'Check Bounds
    If index < 0 Or index >= size Then
        index = list_size - 1
    End If
    'Pull back List
    For i = index To list_size - 1
        Set contents(i) = contents(i + 1)
    Next i
    'ReDim contents(size - 1)
    list_size = list_size - 1
End Sub

Property Get size() As Long
    size = list_size
End Property


Private Sub Class_Initialize()
    list_size = 0
End Sub

Attribute VB_Name = "IntersectionPoint"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
' This class represents an intersection on the bore line from one of the following sources
' SOIL - Soil patches intersecting the bore line. Do not place a bore pit in these.
' DRIVEWAY - Harder surfaces intersecting the bore line (usually concrete or asphalt) that do not cross the road. Bore under these.
' ROAD - Crossing under a road. These intersection points are at the points closest to the R/W before and after crossing the road.
' BRIDGE - The ends of a bridge are projected onto the bore line. Must bore around these like a culvert, but add hand holes on either side.
' CULVERT - Bore underneath these. Culverts are extended (MaximumCulvertDistance) feet to check for bore line intersections. They must cross the centerline to count.
' POLE - Poles close enough (MaxiumumPoleRWDistance) the the R/W are added as these intersection points. It's helpful to place bore pits next to these.
' MATCHLINE - Where matchlines cross the bore line
' GUARDRAIL - Where the guardrail origins are along the bore line. This origin is at one end of the guardrail. Bore pits cannot be placed inside a guard rail.
' END - End of the bore line

' Types for the switch list
' BOREPIT - Represents a bore pit object.
' HANDHOLE - Represents a hand hole object
' BORE - Represents a bore segment. point_distance is the actual length
' PLOW - Represents a plow segment. point_distance is the actual length

Private point_type As String        ' The type of point that this is
Private point_distance As Double    ' The distance along the bore line that this point is at
Private enter_point As Boolean      ' Whether this point enters a feature or exits a feature. This only applies to SOIL, DRIVEWAY, ROAD, BRIDGE

Private Sub Class_Initialize()
    point_type = "NONE"
    point_distance = 0
    enter_point = True
End Sub

Property Get PointType() As String
    PointType = point_type
End Property

Property Get PointDistance() As Double
    PointDistance = point_distance
End Property

Property Get EnterPoint() As Boolean
    EnterPoint = enter_point
End Property

Property Let PointType(pType As String)
    point_type = pType
End Property

Property Let PointDistance(pDistance As Double)
    point_distance = pDistance
End Property

Property Let EnterPoint(enterP As Boolean)
    enter_point = enterP
End Property

Function GetBoreRadius() As Double
    If point_type = "DRIVEWAY" Then
        GetBoreRadius = CDbl(AutoBoreForm.DrivewayBoreRadius)
    ElseIf point_type = "CULVERT" Then
        GetBoreRadius = CDbl(AutoBoreForm.CulvertBoreRadius)
    ElseIf point_type = "BRIDGE" Then
        GetBoreRadius = CDbl(AutoBoreForm.BridgeBoreRadius)
    ElseIf point_type = "GUARDRAIL" Then
        GetBoreRadius = CDbl(AutoBoreForm.GuardrailBoreRadius)
    Else
        GetBoreRadius = 0
    End If
End Function

Function GetDimensionLength() As Double
    If point_type = "BOREPIT" Then
        GetDimensionLength = 4.656 / 2
    ElseIf point_type = "HANDHOLE" Then
        GetDimensionLength = 5.725
    Else
        GetDimensionLength = 0
    End If
End Function

Function isPit() As Boolean
    isPit = point_type = "BOREPIT" Or point_type = "HANDHOLE"
End Function

Attribute VB_Name = "LevelsModule"
Function DisableReferenceLevels()
    Dim oAttachment As Attachment
    Dim oLevel As Level
    Dim referenceName As String
    ' Loop through all reference attachments in the active model
    For Each oAttachment In ActiveModelReference.Attachments
        ' Remove .dgn from the attach name
        referenceName = Left(oAttachment.AttachName, Len(oAttachment.AttachName) - 4)
        ' Loop through each level in the reference
        For Each oLevel In oAttachment.Levels
            If ShouldDisableLevel(referenceName, oLevel.name) Then
                On Error Resume Next ' In case the level can't be modified
                oLevel.IsDisplayed = False
            End If
            On Error GoTo 0
        Next oLevel
    Next oAttachment

    CadInputQueue.SendCommand "FILEDESIGN" ' Refresh the view
End Function

Function ShouldDisableLevel(referenceName As String, levelName As String) As Boolean
    If InStr(levelName, "Scratch_Level") <> 0 _
    Or InStr(levelName, "Old_Level") <> 0 _
    Or levelName = "Default" _
    Then
        ShouldDisableLevel = True
        Exit Function
    End If
    Dim referenceIdentifier As String
    referenceIdentifier = UCase(referenceName)
    If Right(referenceIdentifier, 2) = "FS" Then
        ShouldDisableLevel = ShouldDisableFSLevel(levelName)
        Exit Function
    ElseIf Right(referenceIdentifier, 3) = "DSN" Then
        ShouldDisableLevel = ShouldDisableDSNLevel(levelName)
        Exit Function
    ElseIf Right(referenceIdentifier, 3) = "DRN" Then
        ShouldDisableLevel = ShouldDisableDRNLevel(levelName)
        Exit Function
    ElseIf Right(referenceIdentifier, 3) = "ROW" Then
        ShouldDisableLevel = ShouldDisableROWLevel(levelName)
        Exit Function
    End If
    ShouldDisableLevel = False
End Function

Function ShouldDisableFSLevel(name As String) As Boolean
    If InStr(name, "Exist Vegetation") <> 0 _
    Or (InStr(name, "Exist Utilities") <> 0 And name <> "Exist Utilities Telephone Joint Use Power CELL" And name <> "Exist Utilities Power Pole CELL" And name <> "Exist Utilities Power Joint Use Telephone CELL") _
    Or InStr(name, "Cogo") <> 0 Or InStr(name, "COGO") <> 0 _
    Or (InStr(name, "CTL") <> 0 And InStr(name, "North Arrow") = 0) _
    Or InStr(name, "Exist DTM") <> 0 _
    Or InStr(name, "Exist Horizontal Baseline") <> 0 _
    Or InStr(name, "Exist Roads EOT") <> 0 _
    Or (InStr(name, "Exist Structure Minor Pipes") <> 0 And InStr(name, "Invert") <> 0) _
    Or InStr(name, "Exist Property Tie Line") <> 0 _
    Then
        ShouldDisableFSLevel = True
    Else
        ShouldDisableFSLevel = False
    End If
End Function

Function ShouldDisableDSNLevel(name As String) As Boolean
    If InStr(name, "Superelevation") <> 0 _
    Or (InStr(name, "Prop EOT") And False) <> 0 _
    Or (InStr(name, "Prop Paved Shoulder") And False) <> 0 _
    Or InStr(name, "Prop Lane Lines") <> 0 _
    Or InStr(name, "Prop Dimension") <> 0 _
    Or InStr(name, "Prop Terminator") <> 0 _
    Or InStr(name, "Prop Lane Arrow") <> 0 _
    Then
        ShouldDisableDSNLevel = True
    Else
        ShouldDisableDSNLevel = False
    End If
End Function

Function ShouldDisableDRNLevel(name As String) As Boolean
    If InStr(name, "20 Scale") <> 0 _
    Or (InStr(name, "Prop Earthen Structure") <> 0 And InStr(name, "Detail") <> 0) _
    Or name = "Prop Earthen Structure Ditch Flow Line" _
    Or InStr(name, "Prop Plan Preparation") <> 0 _
    Or InStr(name, "Exist Plan Preparation") <> 0 _
    Or InStr(name, "Prop Drainage Structure Box Number Symbol") <> 0 _
    Or InStr(name, "Cogo") <> 0 Or InStr(name, "COGO") <> 0 _
    Or InStr(name, "Invert") <> 0 _
    Then
        ShouldDisableDRNLevel = True
    Else
        ShouldDisableDRNLevel = False
    End If
End Function

Function ShouldDisableROWLevel(name As String) As Boolean
    If InStr(name, "Prop Easement Construction") <> 0 _
    Then
        ShouldDisableROWLevel = True
    Else
        ShouldDisableROWLevel = False
    End If
End Function

Attribute VB_Name = "LocationModule"
' Check if intersecting other Level 30 lines
' Check if intersecting extended match line

Function moveSelectedDimensionText()
    Debug.Print "Moving Dimension Text"
    ProgressBar.CreateForm "Moving Dimension Text"
    ProgressBar.WriteMessage "0% (Collecting Elements)"
    Dim textElements As New Collection
    Dim fenceEE As ElementEnumerator
    Dim ee As ElementEnumerator
    Dim i As Integer
    'Level 30
    'Get Fence elements
    If ActiveDesignFile.Fence.IsDefined Then
        With ActiveSettings
            .FenceClip = False
            .FenceOverlap = True
        End With
        Set fenceEE = ActiveDesignFile.Fence.GetContents(True)
        While fenceEE.MoveNext
            If fenceEE.Current.IsTextNodeElement And Not fenceEE.Current.Level Is Nothing Then
                If fenceEE.Current.Level.name = "Level 30" And AutoBoreForm.RelocatePitText Then
                    textElements.Add fenceEE.Current
                End If
            End If
        Wend
    End If
    'Get Selected Elements
    Dim ele As Element
    Dim inside As Boolean
    Set ee = ActiveModelReference.GetSelectedElements()
    While ee.MoveNext
        If ee.Current.IsTextNodeElement And Not ee.Current.Level Is Nothing Then
            If ee.Current.Level.name = "Level 30" And AutoBoreForm.RelocatePitText Then
                inside = False
                
                For i = 1 To textElements.count
                    Set ele = textElements.item(i)
                    If DLongToString(ele.ID) = DLongToString(ee.Current.ID) Then
                        inside = True
                        Exit For
                    End If
                Next i
                If Not inside Then textElements.Add ee.Current
            End If
        End If
    Wend
    'CATV
    'Get Fence elements
    If ActiveDesignFile.Fence.IsDefined Then
        fenceEE.Reset
        While fenceEE.MoveNext
            If fenceEE.Current.IsTextNodeElement And Not fenceEE.Current.Level Is Nothing Then
                If fenceEE.Current.Level.name = "CATV Line UBO Text" And AutoBoreForm.RelocateLineDim Then
                    textElements.Add fenceEE.Current
                End If
            End If
        Wend
    End If
    'Get Selected Elements
    ee.Reset
    While ee.MoveNext
        If ee.Current.IsTextNodeElement And Not ee.Current.Level Is Nothing Then
            If ee.Current.Level.name = "CATV Line UBO Text" And AutoBoreForm.RelocateLineDim Then
                
                inside = False
                
                For i = 1 To textElements.count
                    Set ele = textElements.item(i)
                    If DLongToString(ele.ID) = DLongToString(ee.Current.ID) Then
                        inside = True
                        Exit For
                    End If
                Next i
                If Not inside Then textElements.Add ee.Current
            End If
        End If
    Wend
    
    If textElements.count = 0 Then
        MsgBox "No elements selected.", vbExclamation, "Error"
        ActiveDesignFile.Fence.Undefine
        Unload ProgressForm
        Exit Function
    End If
    Dim unMovedElementPositions As New Collection
    Dim point As Point3d
    Dim annotation As Boolean
    For i = 1 To textElements.count
        ProgressBar.UpdateProgress (i - 1), textElements.count, CDbl((i - 1) / textElements.count)
        Set ele = textElements.item(i)
        annotation = (ele.Level.name = "CATV Line UBO Text")
        point = relocateDimension(ele, annotation)
        If point.x <> 0 And point.y <> 0 Then
            unMovedElementPositions.Add point
        End If
    Next i
    
    Debug.Print "Could not move " & unMovedElementPositions.count & " elements"
    
    ActiveDesignFile.Fence.Undefine
    Unload ProgressForm
End Function

' Check if a ray cast from the origin to the center of the map boundary intersects a matchline
Function IsCorrectMapBoundary(origin As Point3d, mapBoundary As ComplexShapeElement) As Boolean
    Dim lineEle As LineElement
    Set lineEle = CreateLineElement2(Nothing, origin, mapBoundary.Centroid)
    Dim nearby As Collection
    Set nearby = Utils.NearbyElements(origin, 200)
    Dim ele As Element
    For i = 1 To nearby.count
        Set ele = nearby.item(i)
        If Not ele.Level Is Nothing Then
            If ele.IsLineElement And ele.Level.name = "Matchline" Then
                ' Matchline
                If UBound(lineEle.GetIntersectionPoints(ele, Matrix3dIdentity)) <> -1 Then
                    ' Line intersects matchline
                    IsCorrectMapBoundary = False
                    Exit Function
                End If
            End If
        End If
    Next i
    IsCorrectMapBoundary = True
End Function


'Get the bore line that the element is on
'Get the map that the center point is in
'Rotate in a circle, finding the closest place to add dimension
'Draw a line to the origin, and make sure it isn't intersecting a centerline
Function relocateDimension(oElem As TextNodeElement, annotationLine As Boolean) As Point3d
    Dim origin As Point3d
    origin = oElem.origin
    Dim boreLine As Element
    Dim mapBoundary As ComplexShapeElement
    Dim centerlines As New Collection
    Dim nearby As Collection
    Dim ee As Element
    Set nearby = Utils.NearbyElements(origin, 500)
    'Get bore line and map boundary
    For i = 1 To nearby.count
        Set ee = nearby.item(i)
        If ee.IsChainableElement() And ee.IsIntersectableElement() And Not ee.Level Is Nothing And boreLine Is Nothing Then
            If ee.Level.name = "Level 30" And Point3dDistance(ee.AsIntersectableElement.ProjectPointOnPerpendicular2(origin, Matrix3dIdentity), origin) < 0.1 Then
                'Bore Line
                Set boreLine = ee
            End If
        End If
        If ee.IsComplexShapeElement And Not ee.Level Is Nothing And mapBoundary Is Nothing Then
            If ee.Level.name = "Level 63" And IsPointInsideComplexShape(origin, ee.AsComplexShapeElement) Then
                'MapBoundary
                If IsCorrectMapBoundary(origin, ee) Then Set mapBoundary = ee
            End If
        End If
    Next i
    If (boreLine Is Nothing And annotationLine) Or mapBoundary Is Nothing Then
        Debug.Print "Could not find map boundary or bore line"
        relocateDimension = origin
        Exit Function
    End If
    'Get centerlines
    Set nearby = Utils.ElementsInside(mapBoundary)
    For i = 1 To nearby.count
        Set ee = nearby.item(i)
        If ee.IsChainableElement And ee.IsIntersectableElement And Not ee.Level Is Nothing Then
            If ee.Level.name = "Exist Horizontal Alignment" Then
                centerlines.Add ee
            End If
        End If
    Next i
    
    Dim nonIntersectingElements As New Collection
    Set nearby = Utils.ElementsInside(mapBoundary)
    For i = 1 To nearby.count
        Set ele = nearby.item(i)
        If ele.IsTextElement Or ele.IsTextNodeElement Or ele.IsDimensionElement Or ele.IsCellElement Then
            nonIntersectingElements.Add ele
        ElseIf Not ele.Level Is Nothing Then
            If ele.Level.name = "Level 30" Then
                nonIntersectingElements.Add ele
            End If
        End If
    Next i
    
    ' Sort through elements to include
    Set nearby = Utils.ElementsInside(mapBoundary.AsClosedElement)
    Dim includedElements As New Collection
    For i = 1 To nearby.count
        Set ele = nearby.item(i)
        If Not ele.Level Is Nothing Then
            If ele.Level.name <> "Level 63" Then
                includedElements.Add ele
            End If
        End If
    Next i
    
    If annotationLine Then
        Dim spaces As New Collection
        Set spaces = FindOpenSpaces(mapBoundary, includedElements, Utils.Max(oElem.Range.high.x - oElem.Range.low.x, oElem.Range.high.y - oElem.Range.low.y) / 2, origin, boreLine.AsChainableElement, centerlines)
        Debug.Print "spaces: " & spaces.count
        Dim noCenterlineCheck As New Collection
        'DrawSpaces spaces ' Used to visualize scores
        For i = 1 To spaces.count
            Dim pt As clsCandidatePoint
            Set pt = spaces.item(i)
            Dim ray As LineElement
            Set ray = CreateLineElement2(Nothing, origin, pt.pt)
            If checkRay(ray, oElem, noCenterlineCheck, mapBoundary, annotationLine, nonIntersectingElements, boreLine) Then
                relocateDimension = Point3dFromXY(0, 0)
                Exit Function
            End If
        Next i
    End If
    Debug.Print "Using fine search"
    relocateDimension = moveToOpenSpot(origin, boreLine, oElem, centerlines, mapBoundary, annotationLine, nonIntersectingElements)
    
End Function

'Draws an annotation line between the boreLine and the element
Function drawAnnotationLine(boreLine As Point3d, oElem As Element)
    Dim lineLevel As Level
    On Error Resume Next
    Set lineLevel = ActiveModelReference.Levels("Level 30")
    If lineLevel Is Nothing Then
        Debug.Print "Annotation line level not found"
        Exit Function
    End If
    Dim lineEle As LineElement
    Dim endPt As Point3d
    endPt = ElementProximity.GetOffsetPointFromElementRange(boreLine, oElem, 20)
    Set lineEle = CreateLineElement2(Nothing, boreLine, endPt)
    Set lineEle.Level = lineLevel
    Set lineEle.LineStyle = ActiveDesignFile.LineStyles.item("0")
    lineEle.LineWeight = 1
    lineEle.Color = 87
    ActiveModelReference.AddElement lineEle
    lineEle.Redraw
    lineEle.Rewrite
End Function

'Gets an open spot for the element that doesn't cross the centerline from the origin, nor is outside the map boundary
'If no open spot can be found, the origin point is returned
Function moveToOpenSpot(origin As Point3d, boreLine As Element, oElem As TextNodeElement, centerlines As Collection, mapBoundary As ComplexShapeElement, annotaionLine As Boolean, nonIntersectingElements As Collection) As Point3d
    'Check if the element is in a good spot already
    If Not areElementsOverlapping(oElem, Point3dFromXY(0, 0), mapBoundary) Then
        Exit Function
    End If
    Dim maxSearchRange As Double
    maxSearchRange = 500
    'Find open spot
    Dim d As Double
    Dim theta As Double
    Dim thetaStep As Double
    Dim rayLonger As LineElement
    Dim distanceStep As Double
    distanceStep = Utils.Min(oElem.Range.high.x - oElem.Range.low.x, oElem.Range.high.y - oElem.Range.low.y)
    For d = distanceStep To maxSearchRange Step distanceStep
        thetaStep = distanceStep / (5 * d)
        Set rayLonger = CreateLineElement2(Nothing, origin, Point3dFromXY(origin.x + d, origin.y))
        For theta = 0 To 6.4 Step thetaStep
            RotateElementAboutZ rayLonger, origin, thetaStep
            rayLonger.Redraw
            If checkRay(rayLonger, oElem, centerlines, mapBoundary, annotaionLine, nonIntersectingElements, boreLine) Then
                moveToOpenSpot = Point3dFromXY(0, 0)
                Exit Function
            End If
        Next theta
    Next d
    Debug.Print "Could not find any open locations"
    moveToOpenSpot = origin
End Function

Function checkRay(ray As LineElement, oElem As TextNodeElement, centerlines As Collection, mapBoundary As ComplexShapeElement, annotationsLine As Boolean, nonIntersectingElements As Collection, boreLine As Element) As Boolean
    Dim moveDistance As Point3d
    moveDistance = Point3dSubtract(ray.endPoint, ray.startPoint)
    If isSpotOpen(ray, oElem, centerlines, mapBoundary) Then
        If annotationsLine Then
            Dim connections As Collection
            Set connections = getAnnotationConnections(boreLine, oElem, ray.endPoint, nonIntersectingElements)
            If connections.count = 0 Or (connections.count = 1 And boreLine.AsChainableElement.length > 800) Then
                checkRay = False
            Else
                'Draw annotations
                oElem.Move moveDistance
                oElem.Rewrite
                oElem.Redraw
                For i = 1 To connections.count
                    moveDistance = connections.item(i)
                    drawAnnotationLine moveDistance, oElem
                Next i
                checkRay = True
            End If
        Else
            oElem.Move moveDistance
            oElem.Rewrite
            oElem.Redraw
            checkRay = True
        End If
    Else
        checkRay = False
    End If
End Function

'Returns points on the boreLine that annotation lines can be made
'Returns Nothing if no connections can be made
Function getAnnotationConnections(boreLine As Element, textEle As TextNodeElement, textLocation As Point3d, nonIntersectingElements As Collection) As Collection
    Dim connections As New Collection
    Dim point As Point3d
    If boreLine.AsChainableElement.length > 650 Then
        ' 2 lines
        point = getConnection(boreLine, 0, boreLine.AsChainableElement.length / 2, textEle, textLocation, nonIntersectingElements)
        If point.x <> 0 Or point.y <> 0 Then
            connections.Add point
        Else
            'Debug.Print "Could not get second connection for annotation line 1"
        End If
        point = getConnection(boreLine, boreLine.AsChainableElement.length / 2, boreLine.AsChainableElement.length, textEle, textLocation, nonIntersectingElements)
        If point.x <> 0 Or point.y <> 0 Then
            connections.Add point
        Else
            'Debug.Print "Could not get second connection for annotation line 2"
        End If
    Else
        '1 line
        point = getConnection(boreLine, 0, boreLine.AsChainableElement.length, textEle, textLocation, nonIntersectingElements)
        If point.x <> 0 Or point.y <> 0 Then
            connections.Add point
        Else
            'Debug.Print "Could not get second connection for annotation line"
        End If
    End If
    
    Set getAnnotationConnections = connections
End Function

Function getConnection(boreLine As Element, minLength As Double, maxLength As Double, textEle As TextNodeElement, textLocation As Point3d, nonIntersectingElements As Collection) As Point3d
    Dim point As Point3d
    Dim flip As Integer
    flip = 1
    Dim middle As Double
    middle = (maxLength + minLength) / 2
    Dim ray As LineElement
    Dim d As Long
    Dim ee As Element
    Dim noIntersections As Boolean
    Dim distance As Double
    For d = 0 To (maxLength - minLength) / 2 Step 10
        distance = middle + (d * flip)
        If distance > maxLength Or distance < 0 Then
            Exit For
        End If
        point = boreLine.AsChainableElement.PointAtDistance(middle + (d * flip))
        Set ray = CreateLineElement2(Nothing, textLocation, point)
        noIntersections = True
        For i = 1 To nonIntersectingElements.count
            Set ee = nonIntersectingElements.item(i)
            If DLongToString(ee.ID) <> DLongToString(textEle.ID) Then
                If ee.IsIntersectableElement Then
                    If DLongToString(ee.ID) <> DLongToString(boreLine.ID) And UBound(ray.GetIntersectionPoints(ee, Matrix3dIdentity)) <> -1 Then
                        'Point is not good
                        noIntersections = False
                        Exit For
                    End If
                Else
                    If DoesLineOverlapBoundingBox(ray, ee) Then
                        'Point is not good
                        noIntersections = False
                        Exit For
                    End If
                End If
            End If
        Next i
        If noIntersections Then
            getConnection = point
            Exit Function
        End If
        flip = flip * -1
    Next d
    getConnection = Point3dFromXY(0, 0)
End Function

Function areElementsOverlapping(oElem As Element, modifier As Point3d, mapBoundary As ComplexShapeElement)
    Dim boundingBox As ClosedElement
    Dim verticies(0 To 3) As Point3d
    verticies(0) = Point3dAdd(oElem.Range.high, modifier)
    verticies(1) = Point3dAdd(Point3dFromXY(oElem.Range.high.x, oElem.Range.low.y), modifier)
    verticies(2) = Point3dAdd(oElem.Range.low, modifier)
    verticies(3) = Point3dAdd(Point3dFromXY(oElem.Range.low.x, oElem.Range.high.y), modifier)
    Set boundingBox = CreateShapeElement1(Nothing, verticies)
    
    Dim nearby As Collection
    Set nearby = Utils.ElementsInside(boundingBox)
    Dim ee As Element
    For i = 1 To nearby.count
        Set ee = nearby.item(i)
        If Not ee.Level Is Nothing Then
            If DLongToString(ee.ID) <> DLongToString(oElem.ID) Then
                If ee.Level.name = "Level 63" Then
                    'Check if the element is the map boundary
                    If DLongToString(ee.ID) = DLongToString(mapBoundary.ID) Then
                        'Too close to map boundary
                        areElementsOverlapping = True
                        Exit Function
                    End If
                Else
                    'Intersecting element
                    areElementsOverlapping = True
                    Exit Function
                End If
            End If
        Else
            'Intersecting element - possibly cell header
            areElementsOverlapping = True
            Exit Function
        End If
    Next i
    checkOverlappingElements = False
End Function

Function isSpotOpen(ray As LineElement, oElem As Element, centerlines As Collection, mapBoundary As ComplexShapeElement) As Boolean
    Dim modifier As Point3d
    modifier = Point3dSubtract(ray.endPoint, ray.startPoint)
    If areElementsOverlapping(oElem, modifier, mapBoundary) Then
        isSpotOpen = False
        Exit Function
    End If
    
    Dim ee As Element
    
    'Check if ray intersects centerlines
    Dim intersections() As Point3d
    For i = 1 To centerlines.count
        Set ee = centerlines.item(i)
        If UBound(ray.GetIntersectionPoints(ee, Matrix3dIdentity)) <> -1 Then
            'Intersects centerline
            isSpotOpen = False
            Exit Function
        End If
    Next i
    'Check if ray intersects map boundary
    If UBound(ray.GetIntersectionPoints(mapBoundary, Matrix3dIdentity)) <> -1 Then
        'Intersects
        isSpotOpen = False
        Exit Function
    End If
    isSpotOpen = True
End Function

Function IsPointInsideComplexShape(point As Point3d, complexShape As ComplexShapeElement) As Boolean
    Dim vertices(0 To 3) As Point3d
    Dim enumerator As ElementEnumerator
    Dim elem As Element
    Dim i As Integer
    

    ' Get the sub-elements of the complex shape
    Set enumerator = complexShape.GetSubElements()

    ' Collect vertices from the sub-elements
    Do While enumerator.MoveNext
        Set elem = enumerator.Current
        vertices(i) = elem.AsLineElement.startPoint
        i = i + 1
    Loop

    ' Use Point3dInPolygonXY to test if the point is inside the shape
    If UBound(vertices) >= 2 Then
        IsPointInsideComplexShape = Point3dInPolygonXY(point, vertices) = 1
    Else
        IsPointInsideComplexShape = False
    End If
    
End Function

Function DoesLineOverlapBoundingBox(lineElem As LineElement, elem As Element) As Boolean
    Dim rangeLow As Point3d, rangeHigh As Point3d
    Dim p1 As Point3d, p2 As Point3d
    
    ' Get element's range
    Dim rng As Range3d
    rng = elem.Range
    rangeLow = rng.low
    rangeHigh = rng.high

    p1 = lineElem.startPoint
    p2 = lineElem.endPoint
    
    ' 1. Check if either endpoint is inside the bounding box
    If IsPointInBox(p1, rangeLow, rangeHigh) Or IsPointInBox(p2, rangeLow, rangeHigh) Then
        DoesLineOverlapBoundingBox = True
        Exit Function
    End If

    ' 2. Check intersection with bounding box edges
    ' Define box edges
    Dim bl As Point3d, br As Point3d, tr As Point3d, tl As Point3d
    bl = Point3dFromXY(rangeLow.x, rangeLow.y)   ' Bottom Left
    br = Point3dFromXY(rangeHigh.x, rangeLow.y)  ' Bottom Right
    tr = Point3dFromXY(rangeHigh.x, rangeHigh.y) ' Top Right
    tl = Point3dFromXY(rangeLow.x, rangeHigh.y)  ' Top Left

    ' Check line intersection with each edge
    If SegmentsIntersect(p1, p2, bl, br) Then DoesLineOverlapBoundingBox = True: Exit Function
    If SegmentsIntersect(p1, p2, br, tr) Then DoesLineOverlapBoundingBox = True: Exit Function
    If SegmentsIntersect(p1, p2, tr, tl) Then DoesLineOverlapBoundingBox = True: Exit Function
    If SegmentsIntersect(p1, p2, tl, bl) Then DoesLineOverlapBoundingBox = True: Exit Function

    ' If none of the above, no overlap
    DoesLineOverlapBoundingBox = False
End Function

Private Function IsPointInBox(pt As Point3d, boxLow As Point3d, boxHigh As Point3d) As Boolean
    If pt.x >= boxLow.x And pt.x <= boxHigh.x And pt.y >= boxLow.y And pt.y <= boxHigh.y Then
        IsPointInBox = True
    Else
        IsPointInBox = False
    End If
End Function

' This helper function checks if two line segments (p1-p2 and p3-p4) intersect in 2D
Private Function SegmentsIntersect(p1 As Point3d, p2 As Point3d, p3 As Point3d, p4 As Point3d) As Boolean
    Dim line1 As LineElement
    Dim line2 As LineElement
    Set line1 = CreateLineElement2(Nothing, p1, p2)
    Set line2 = CreateLineElement2(Nothing, p3, p4)
    SegmentsIntersect = UBound(line1.GetIntersectionPoints(line2, Matrix3dIdentity)) <> -1
End Function

Function DrawSpaces(spaces As Collection)
    Dim space As clsCandidatePoint
    Dim textEle As TextElement
    For i = 1 To spaces.count
        Set space = spaces.item(i)
        Set textEle = CreateTextElement1(Nothing, CStr(Round(space.score, 2)), space.pt, Matrix3dIdentity)
        If i = 1 Then
            textEle.Color = 2
        Else
            textEle.Color = 4
        End If
        
        ActiveModelReference.AddElement textEle
        textEle.Redraw
    Next i
End Function

Function DrawUnscoredSpaces(spaces() As clsCandidatePoint)
    Dim space As clsCandidatePoint
    Dim circ As EllipseElement
    For i = LBound(spaces) To UBound(spaces)
        Set space = spaces(i)
        Set circ = CreateEllipseElement2(Nothing, space.pt, 5, 5, Matrix3dIdentity)
        If i = 1 Then
            circ.Color = 2
        Else
            circ.Color = 4
        End If
        
        ActiveModelReference.AddElement circ
        circ.Redraw
    Next i
End Function

Attribute VB_Name = "MatchlineModule"
'Iterate through each boundary
'get inside contents & find level 63 shapes
'Create shape elements with furthest intersection points & get area
'Check if area above a 20000 (set option)
'Check if no other matchlines exist
'Matchline will have same orientation as longest side of the cutout
'Find a centerline inside the cutout
'Try and find a place along the centerline that doesn't cut off specific items:
'Text, complex shape elements, culverts


Function CreateMatchlines()
    Debug.Print "Auto Matchline Start"
    If Not ActiveDesignFile.Fence.IsDefined Then
        MsgBox "Fence is not defined"
        Exit Function
    End If
    Dim completedLines As New Collection
    'Scan for boundaries
    Dim ee As ElementEnumerator
    Dim firstFence As Fence
    
     With ActiveSettings
        .FenceClip = False
        .FenceOverlap = True
    End With

    Set firstFence = ActiveDesignFile.Fence
    Set ee = firstFence.GetContents(False)
    ee.Reset
    Dim boundary As ComplexShapeElement
    While ee.MoveNext
        If ee.Current.IsComplexShapeElement Then
            If ee.Current.Level.name = "Level 63" Then
                Set boundary = ee.Current
                'Get overlapping boundaries
                Dim oFence As Fence
                Dim oElem As Element
                Dim myView As View
                
                With ActiveSettings
                    .FenceClip = False
                    .FenceOverlap = True
                End With
            
                Set oFence = ActiveDesignFile.Fence
                oFence.Undefine
            
                Set myView = CommandState.LastView
            
                oFence.DefineFromElement myView, boundary
                oFence.Draw
                
                Dim fenceEE As ElementEnumerator
                Set fenceEE = oFence.GetContents(True)
                Dim mapNum As String
                mapNum = getMapNum(boundary)
                Dim otherMapNum As String
                Dim center As Point3d
                Dim completed As Boolean
                Dim compa As String
                Dim compb As String
                'Iterate through contents
                While fenceEE.MoveNext
                    Set oElem = fenceEE.Current
                    'Check for boundary
                    If oElem.IsComplexShapeElement Then
                        If oElem.Level.name = "Level 63" Then
                            'Get map number
                            otherMapNum = getMapNum(oElem.AsComplexShapeElement)
                            If otherMapNum <> mapNum Then
                                completed = False
                                For i = 1 To completedLines.count
                                    compa = Split(completedLines.item(i), ":")(0)
                                    compb = Split(completedLines.item(i), ":")(1)
                                    'Debug.Print "comparing " & compa & " and " & compb
                                    If compa = mapNum And compb = otherMapNum Then
                                        completed = True
                                        Exit For
                                    ElseIf compa = otherMapNum And compb = mapNum Then
                                        completed = True
                                        Exit For
                                    End If
                                Next i
                                If Not completed Then
                                    center = getCenter(boundary, oElem.AsComplexShapeElement)
                                    Debug.Print mapNum & " : " & otherMapNum
                                    completedLines.Add mapNum & " : " & otherMapNum
                                    
                                    If isMap1Above(boundary, oElem.AsComplexShapeElement) Then
                                        PlaceMatchline center, getRotationType(boundary, oElem.AsComplexShapeElement), mapNum, otherMapNum
                                    Else
                                        PlaceMatchline center, getRotationType(boundary, oElem.AsComplexShapeElement), otherMapNum, mapNum
                                    End If
                                End If
                            End If
                        End If
                    End If
                Wend
            End If
        End If
    Wend
    ActiveDesignFile.Fence.Undefine
End Function

Function getCenter(map1 As ComplexShapeElement, map2 As ComplexShapeElement) As Point3d
        'Get overlapping boundaries
        Debug.Print "Finding center between maps"
        Dim oFence As Fence
        Dim oElem As Element
        Dim myView As View
        
        With ActiveSettings
            .FenceClip = True
            .FenceOverlap = True
        End With
    
        Set oFence = ActiveDesignFile.Fence
        oFence.Undefine
    
        Set myView = CommandState.LastView
    
        oFence.DefineFromElement myView, map1
        oFence.Draw
        
        Dim fenceEE As ElementEnumerator
        Set fenceEE = oFence.GetContents(True)
        
        Dim map1Verticies(4) As Point3d
        Dim map2Verticies() As Point3d
        Dim ee As ElementEnumerator
        Set ee = map2.GetSubElements
        For i = 0 To 3
            ee.MoveNext
            map1Verticies(i) = ee.Current.AsLineElement.startPoint
        Next i
        Dim found As Boolean
        found = False
        While fenceEE.MoveNext
            Set oElem = fenceEE.Current
            ActiveModelReference.RemoveElement oElem
            'Check if boundary
            If Not found Then
                If oElem.IsShapeElement Then
                    If oElem.Level.name = "Level 63" Then
                        'Check if it shares one of the same verticies of map2
                         map2Verticies = oElem.AsShapeElement.GetVertices
                        For i = 0 To oElem.AsShapeElement.VerticesCount - 1
                            For j = 0 To 3
                                If Point3dDistance(map2Verticies(i), map1Verticies(j)) < 0.01 Then
                                    'vertex matches
                                    getCenter = getCenterCenterline(oElem.AsShapeElement)
                                    Debug.Print "Found Center"
                                    found = True
                                End If
                            Next j
                        Next i
                    End If
                End If
            End If
        Wend
        If found Then Exit Function
    'return midpoint between maps
    Debug.Print "Could not get overlapping area"
    Dim x As Double
    Dim y As Double
    x = 0
    y = 0
    Set ee = map2.GetSubElements
    For i = 0 To 3
        ee.MoveNext
        x = x + ee.Current.AsLineElement.startPoint.x
        y = y + ee.Current.AsLineElement.startPoint.y
        x = x + map1Verticies(i).x
        y = y + map1Verticies(i).y
    Next i
    x = x / 8
    y = y / 8
    getCenter = Point3dFromXY(x, y)
End Function

Function getCenterCenterline(boundary As ShapeElement) As Point3d
    Dim oFence As Fence
    Dim oElem As Element
    Dim myView As View
    
    With ActiveSettings
        .FenceClip = True
        .FenceOverlap = True
    End With

    Set oFence = ActiveDesignFile.Fence
    oFence.Undefine

    Set myView = CommandState.LastView

    oFence.DefineFromElement myView, boundary
    oFence.Draw
    
    Dim fenceEE As ElementEnumerator
    Set fenceEE = oFence.GetContents(True)
    Dim found As Boolean
    found = False
    While fenceEE.MoveNext
        Set oElem = fenceEE.Current
        If Not found Then
            If oElem.IsChainableElement Then
                If oElem.Level.name = "Exist Horizontal Alignment" Then
                    getCenterCenterline = oElem.AsChainableElement.PointAtDistance(oElem.AsChainableElement.length / 2)
                    found = True
                End If
            End If
        End If
        ActiveModelReference.RemoveElement oElem
    Wend
    If found Then Exit Function
    Debug.Print "Couldn't find containing road"
    getCenterCenterline = boundary.Centroid
End Function

Function getRotationType(map1 As ComplexShapeElement, map2 As ComplexShapeElement) As Integer
    Dim reference As Point3d
    reference = Point3dFromXY(1, 0)
    Dim vectorBetween As Point3d
    vectorBetween = Point3dSubtract(map2.Centroid, map1.Centroid)
    Dim angle As Double
    angle = Point3dAngleBetweenVectorsXY(reference, vectorBetween)
    angle = 180 * angle / Pi
    
    '20-30 degrees = 3
    '(-160)-(-150) degrees = 3
    '(-20)-(-30) degrees = 4
    '160-150 degrees = 4
    '(-20)-20 degrees = 2
    '160-180 degrees = 2
    '(-160)-(-180) degrees = 2
    '30-150 degrees = 1
    '(-30)-(-150) degrees = 1
    Dim rotationType As Integer
    If (angle > 20 And angle < 30) Or (angle > -150 And angle < -160) Then
        rotationType = 2 '3
    ElseIf (angle > -30 And angle < -20) Or (angle > 150 And angle < 160) Then
        rotationType = 2 '4
    ElseIf (angle > 30 And angle < 150) Or (angle > -150 And angle < -30) Then
        rotationType = 1
    Else
        rotationType = 2
    End If
    Debug.Print "Rotation: " & rotationType & " angle: " & angle
    getRotationType = rotationType
End Function

Function isMap1Above(map1 As ComplexShapeElement, map2 As ComplexShapeElement) As Boolean
    Dim reference As Point3d
    reference = Point3dFromXY(1, 0)
    Dim vectorBetween As Point3d
    vectorBetween = Point3dSubtract(map2.Centroid, map1.Centroid)
    Dim angle As Double
    angle = Point3dAngleBetweenVectorsXY(reference, vectorBetween)
    angle = 180 * angle / Pi
    
    'below if angle is 30-(-150)
    
    Dim above As Boolean
    If angle > -150 And angle < 30 Then
        above = False
    Else
        above = True
    End If
    isMap1Above = above
End Function

Function getMapNum(boundary As ComplexShapeElement) As String
    Dim oFence As Fence
        Dim oElem As Element
        Dim myView As View
        
        With ActiveSettings
            .FenceClip = False
            .FenceOverlap = True
        End With
    
        Set oFence = ActiveDesignFile.Fence
        oFence.Undefine
    
        Set myView = CommandState.LastView
    
        oFence.DefineFromElement myView, boundary
        oFence.Draw
        
        Dim fenceEE As ElementEnumerator
        Set fenceEE = oFence.GetContents(True)
        
        'Iterate through contents
        Dim mapEle As Element
        While fenceEE.MoveNext
            Set mapEle = fenceEE.Current
            If mapEle.IsTextElement Then
                If mapEle.Level.name = "Level 62" Then
                    getMapNum = Right(mapEle.AsTextElement.text, Len(mapEle.AsTextElement.text) - 4)
                    Exit Function
                End If
            End If
        Wend
        getMapNum = "0"
End Function

'Rotation Types:
'1=Horizontal
'2=Vertical
'3=Downward slope
'4=Upward slope
Function PlaceMatchline(center As Point3d, rotationType As Integer, aboveNum As String, belowNum As String)
    Debug.Print "Placing matchline at " & center.x & " " & center.y
    Dim line As LineElement
    Set line = ActiveModelReference.CopyElement(GetMatchLineTemplate())
    Dim linemidpt As Point3d
    linemidpt = Point3dScale(Point3dAdd(line.startPoint, line.endPoint), 0.5)
    Dim text1 As TextElement
    Set text1 = ActiveModelReference.CopyElement(GetMatchTextTemplate())
    Dim text2 As TextElement
    Set text2 = ActiveModelReference.CopyElement(GetMatchTextTemplate())
    'RotateAboutZ
    Dim rotationAngle As Double
    rotationAngle = Switch(rotationType = 1, 0, rotationType = 2, 1.5708, rotationType = 3, 5.4978, rotationType = 4, 0.7854)
    line.RotateAboutZ linemidpt, rotationAngle
    text1.RotateAboutZ text1.origin, rotationAngle
    text2.RotateAboutZ text1.origin, rotationAngle
    
    Dim moveDistance As Point3d
    moveDistance = Point3dSubtract(center, linemidpt)
    line.Move moveDistance
    
    Dim above As Point3d
    above = Point3dAdd(Point3dScale(Point3dRotateXY(Point3dNormalize(Point3dSubtract(line.endPoint, line.startPoint)), 1.5708), 13), center)
    Dim below As Point3d
    below = Point3dAdd(Point3dScale(Point3dNormalize(Point3dSubtract(center, above)), 3.5), center)
    
    text1.text = "MATCHLINE -L-  SEE SHEET " & aboveNum
    text2.text = "MATCHLINE -L-  SEE SHEET " & belowNum
    
    moveDistance = Point3dSubtract(above, text1.origin)
    text1.Move moveDistance
    moveDistance = Point3dSubtract(below, text2.origin)
    text2.Move moveDistance
    
    line.Redraw
    line.Rewrite
    text1.Redraw
    text1.Rewrite
    text2.Redraw
    text2.Rewrite

End Function

Function GetMatchLineTemplate() As LineElement
    Static matchline As LineElement
    If matchline Is Nothing Then
        'Find line
        Dim ee As ElementEnumerator
        If ActiveModelReference.AnyElementsSelected Then
            Set ee = ActiveModelReference.GetSelectedElements()
        Else
            Dim oScanCriteria As ElementScanCriteria
            Set oScanCriteria = New ElementScanCriteria
            oScanCriteria.ExcludeAllLevels
            oScanCriteria.IncludeLevel ActiveDesignFile.Levels("Matchline")
            oScanCriteria.ExcludeAllTypes
            oScanCriteria.IncludeType msdElementTypeLine
            Set ee = ActiveModelReference.Scan(oScanCriteria)
        End If
        Dim oElem As Element
        Do While ee.MoveNext
            Set oElem = ee.Current
            If Not oElem.Level Is Nothing Then
                If oElem.Level.name = "Matchline" And oElem.IsLineElement Then
                    Set matchline = oElem
                    Exit Do
                End If
            End If
        Loop
        If Not matchline Is Nothing Then
            Set GetMatchLineTemplate = matchline
            Debug.Print "Using matchline at " & matchline.origin.x & " " & matchline.origin.y
        Else
            Debug.Print "No match line template"
            MsgBox "No matchline template in design file.", vbCritical, "Error"
            End
        End If
    Else
        Set GetMatchLineTemplate = matchline
    End If
End Function

Function GetMatchTextTemplate() As TextElement
    Static matchText As TextElement
    If matchText Is Nothing Then
        'Find text
        Dim ee As ElementEnumerator
        If ActiveModelReference.AnyElementsSelected Then
            Set ee = ActiveModelReference.GetSelectedElements()
        Else
            Dim oScanCriteria As ElementScanCriteria
            Set oScanCriteria = New ElementScanCriteria
            oScanCriteria.ExcludeAllLevels
            oScanCriteria.IncludeLevel ActiveDesignFile.Levels("Matchline")
            oScanCriteria.ExcludeAllTypes
            oScanCriteria.IncludeType msdElementTypeText
            Set ee = ActiveModelReference.Scan(oScanCriteria)
        End If
        Dim oElem As Element
        Do While ee.MoveNext
            Set oElem = ee.Current
            If Not oElem.Level Is Nothing Then
                If oElem.Level.name = "Matchline" And oElem.IsTextElement Then
                    Set matchText = oElem
                    Exit Do
                End If
            End If
        Loop
        If Not matchText Is Nothing Then
            Set GetMatchTextTemplate = matchText
        Else
            Debug.Print "No match text template"
            MsgBox "No matchline template in design file.", vbCritical, "Error"
        End If
    Else
        Set GetMatchTextTemplate = matchText
    End If
End Function

Attribute VB_Name = "PointList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private contents(999) As ActionPoint

Private list_size As Long

Property Get At(index As Long) As ActionPoint
    Set At = contents(index)
End Property

Public Sub SetPointDistance(index As Long, distance As Double)
    If index < list_size Then
        contents(index).PointDistance = distance
    End If
End Sub

Public Sub SetPointVariant(index As Long, newVariant As Boolean)
    If index < list_size Then
        contents(index).VariantType = newVariant
    End If
End Sub

Public Sub SortList()
    Arrays.QuickActionSort contents, 0, list_size - 1
End Sub


Public Sub Add(item As ActionPoint, Optional index As Long = -1)
    'Make sure index is in bounds
    If index < 0 Or index > list_size Then
        index = list_size
    End If
    'Change array size
    'ReDim contents(list_size + 1)
    If index = list_size Then
        Set contents(index) = item
    Else
        'Push everything back
        Dim tempVal As ActionPoint
        Dim tempVal2 As ActionPoint
        Set tempVal = contents(index)
        Set contents(index) = item
        For i = index + 1 To list_size - 1
            Set tempVal2 = contents(i)
            Set contents(i) = tempVal
            Set tempVal = tempVal2
        Next i
        Set contents(list_size) = tempVal
    End If
    list_size = list_size + 1
End Sub

Property Get ToArray() As Variant
    ToArray = contents
End Property

Public Sub PrintPoints()
    For i = 0 To list_size - 1
        Debug.Print i & ": " & contents(i).PointDistance & " = " & contents(i).PointType
    Next i
End Sub

Public Sub Remove(index As Long)
    'Check Bounds
    If index < 0 Or index >= size Then
        index = list_size - 1
    End If
    'Pull back List
    For i = index To list_size - 1
        Set contents(i) = contents(i + 1)
    Next i
    'ReDim contents(size - 1)
    list_size = list_size - 1
End Sub

Property Get size() As Long
    size = list_size
End Property


Private Sub Class_Initialize()
    list_size = 0
End Sub

Attribute VB_Name = "PolesModule"
Function MovePoles()
    Debug.Print qrqrqrqr; "Moving Poles"
    Dim maxDistance As Double
    maxDistance = CDbl(AutoBoreForm.PoleDistanceInRW)
    
    ProgressBar.CreateForm "Checking Poles"
    ProgressBar.WriteMessage "0% (Counting Poles)"

    Dim ee As ElementEnumerator
    If ActiveDesignFile.Fence.IsDefined Then
        Dim firstFence As Fence
    
        With ActiveSettings
            .FenceClip = False
            .FenceOverlap = True
        End With
    
        Set firstFence = ActiveDesignFile.Fence
        Set ee = firstFence.GetContents(False)
    Else
        Dim oScanCriteria As ElementScanCriteria
        Set oScanCriteria = New ElementScanCriteria
        oScanCriteria.ExcludeAllTypes
        oScanCriteria.IncludeType msdElementTypeCellHeader
        oScanCriteria.IncludeType msdElementTypeCellLibraryHeader
        oScanCriteria.IncludeType msdElementTypeText
    
        Set ee = ActiveModelReference.Scan(oScanCriteria)
    End If
    
    'Count poles
    Dim oElem As Element
    Dim numPoles As Integer
    numPoles = 0
    While ee.MoveNext
        Set oElem = ee.Current
        If oElem.IsCellElement Then
            If oElem.AsCellElement.name = "EXIST UTILITIES POWER JOINT USE TELEPHONE" Then
                numPoles = numPoles + 1
            End If
        ElseIf oElem.IsTextElement Then
            If oElem.Level.name = "Sheet Symbology CELL" Then
                numPoles = numPoles + 1
            End If
        End If
    Wend
    ee.Reset
    
    Dim poleNum As Integer
    poleNum = 0
    Dim isPole As Boolean
    Dim origin As Point3d
    While ee.MoveNext
        isPole = False
        Set oElem = ee.Current
        If oElem.IsCellElement Then
            If oElem.AsCellElement.name = "EXIST UTILITIES POWER JOINT USE TELEPHONE" Then
                isPole = True
                origin = oElem.AsCellElement.origin
            End If
        ElseIf oElem.IsTextElement Then
            If oElem.Level.name = "Sheet Symbology CELL" Then
                isPole = True
                origin = oElem.AsTextElement.origin
            End If
        End If
        If isPole Then
            poleNum = poleNum + 1
            Debug.Print "Checking pole: " & poleNum
            ProgressBar.UpdateProgress poleNum, numPoles, CDbl(poleNum / numPoles)
            Dim outside As Point3d
            outside = GetOutsideRW(origin, maxDistance)
            If Point3dDistance(outside, origin) > 0.1 Then
                'Move
                Dim moveDistance As Point3d
                moveDistance = Point3dSubtract(outside, origin)
                'Debug.Print moveDistance.x & " " & moveDistance.y
                oElem.Move moveDistance
                oElem.Redraw
                oElem.Rewrite
            End If
        End If
    Wend
    ActiveDesignFile.Fence.Undefine
    Unload ProgressForm
End Function

Function GetOutsideRW(point As Point3d, maxDistance As Double) As Point3d
        Const poleThickness As Double = 3
        Dim nearby As Collection
        Set nearby = Utils.NearbyElements(point, 100)
        Dim oElem As Element
        Dim currPoint As Point3d
        Dim centerLine As Point3d
        centerLine = point
        Dim rw As Point3d
        rw = point
        Dim rwElement As Element
        For i = 1 To nearby.count
            Set oElem = nearby.item(i)
            If oElem.IsIntersectableElement Then
                If oElem.Level.name = "Exist Horizontal Alignment" Then
                    currPoint = oElem.AsIntersectableElement.ProjectPointOnPerpendicular2(point, Matrix3dIdentity)
                    'Debug.Print currPoint.x & " " & currPoint.y
                    
                    If currPoint.x & "" <> "-nan(ind)" Then
                        If Point3dDistance(centerLine, point) < 0.1 Or Point3dDistance(centerLine, point) > Point3dDistance(currPoint, point) Then
                            'Closer
                            centerLine = currPoint
                        End If
                    End If
                ElseIf oElem.Level.name = "Exist Right of Way Line" Then
                    currPoint = oElem.AsIntersectableElement.ProjectPointOnPerpendicular2(point, Matrix3dIdentity)
                    If currPoint.x & "" <> "-nan(ind)" Then
                        If Point3dDistance(rw, point) < 0.1 Or Point3dDistance(rw, point) > Point3dDistance(currPoint, point) Then
                            'Closer
                            rw = currPoint
                            Set rwElement = oElem
                        End If
                    End If
                End If
            End If
        Next i
        
        If Point3dDistance(point, rw) < maxDistance And Point3dDistance(point, rw) > 0.01 And Point3dDistance(point, centerLine) > 0.01 Then
            Debug.Print "Checking position"
            'Get angle between rw and centerline
            Dim angle As Double
            angle = Point3dAngleBetweenVectorsXY(Point3dSubtract(rw, point), Point3dSubtract(centerLine, point))
            Dim outsideVector As Vector3d
            Dim outside As Point3d
            If Abs(angle) > (Pi / 2) Then
                'inside R/W
                'Move out of R/W
                
                outsideVector = Vector3dSubtractPoint3dPoint3d(rw, point)
                
                outside = Point3dAddScaledVector3d(point, outsideVector, 1)
                outside = Point3dAddScaledVector3d(outside, Vector3dNormalize(outsideVector), poleThickness)
                GetOutsideRW = outside
                Debug.Print "Needs adjusting"
                Exit Function
            Else
                'Check if too close to  R/W
                If Point3dDistance(point, rw) < 2.5 Then
                    outsideVector = Vector3dScale(Vector3dNormalize(Vector3dSubtractPoint3dPoint3d(point, rw)), 2.5 - Point3dDistance(point, rw))
                    outside = Point3dAddScaledVector3d(point, outsideVector, 1)
                    GetOutsideRW = outside
                    Debug.Print "Too close"
                    Exit Function
                End If
            End If
        End If
        GetOutsideRW = point
End Function

Attribute VB_Name = "ProgressBar"
Function CreateForm(titleCaption As String)
    Load ProgressForm
    With ProgressForm
        .StartUpPosition = 0
        .Left = Application.LeftPosition + (0.5 * Application.width) - (0.5 * .width)
        .Top = Application.TopPosition + (0.5 * Application.height) - (0.5 * .height)
        .Caption = titleCaption
        .Show vbModeless
    End With
End Function

Function UpdateProgress(CurrNum As Integer, TargetNum As Integer, percentProgress As Double)
    Dim displayProgress As Integer
    displayProgress = CInt(percentProgress * 100)
    With ProgressForm
        .FrameProgress.Caption = displayProgress & "% (" & CurrNum & "/" & TargetNum & ")"
        .LabelProgress.width = percentProgress * (.FrameProgress.width - 15) + 1
        .Repaint
    End With
    DoEvents
End Function

Function WriteMessage(msg As String)
    ProgressForm.FrameProgress.Caption = msg
    ProgressForm.Repaint
    DoEvents
End Function

Attribute VB_Name = "PropertyLineModule"
'Auto Format Property Lines
'Break up shape elements
'Create a list of vertex points and a connection list
'Cut lines to current R/W
'Delete nearest vertex and its connections
'Extend lines a constant distance & check for intersection
'Connect to R/W if no other property line intersection occurs first
'Delete vertex and its connections

'Auto Dimension Property Lines
'Iterate through each map
'Get all property lines
'Check for minimum distance
'Check if it intersects the boundary
'Label in the center of end points or where it intersects the boundary
'Check for nearby objects in polygon pattern
'Move left and right a little every time to find an open space
'Reset at center if no open space is found

'Check line distance after cutting
'Don't place if there is already an overlapping dimension
'Reduce default dim minimum - 30
'Smaller locate increments
'Cannot dimension < half of min dimension away from edge

Public Function DimensionProperty()
    Debug.Print "Auto Dimension Property Start"
    If Not ActiveDesignFile.Fence.IsDefined Then
        MsgBox "Fence is not defined"
        Exit Function
    End If
    MS_DISABLEWINDOWGHOSTING = 1
    'Create level if necessary
    Dim dimLevel As Level
    If ActiveModelReference.Levels.Find("Exist Property Line Text") Is Nothing Then
        Set dimLevel = ActiveDesignFile.AddNewLevel("Exist Property Line Text")
        dimLevel.ElementColor = 5
        dimLevel.ElementLineWeight = 1
        dimLevel.ElementLineStyle = ActiveDesignFile.LineStyles("NCDOT Leader Medium")
        ActiveModelReference.Levels.Rewrite
    Else
        Set dimLevel = ActiveModelReference.Levels("Exist Property Line Text")
    End If
    
    
    Dim minLength As Double
    minLength = CDbl(AutoBoreForm.MinDimLength)
    Dim ee As ElementEnumerator
    Dim firstFence As Fence
    
     With ActiveSettings
        .FenceClip = False
        .FenceOverlap = True
    End With

    Set firstFence = ActiveDesignFile.Fence
    Set ee = firstFence.GetContents(False)
    ee.Reset
    Dim boundary As ComplexShapeElement
    Dim boundaries As New Collection
    'Set up progress notification
    Dim numBoundaries As Integer
    numBoundaries = 0
    While ee.MoveNext
        If ee.Current.IsComplexShapeElement Then
        Debug.Print ee.Current.Level.name
            If ee.Current.Level.name = "Level 63" Then
                
                boundaries.Add ee.Current
                numBoundaries = numBoundaries + 1
            End If
        End If
    Wend
    Dim currentBoundaryNum As Integer
    currentBoundaryNum = 0
    Debug.Print "Number of boundaries: " & numBoundaries
    'Utils.displayProgress
    'Iterate through scanned boundaries
    For o = 1 To boundaries.count
        currentBoundaryNum = currentBoundaryNum + 1
        Dim progress As Double
        progress = currentBoundaryNum / numBoundaries
        Debug.Print "Progress: " & progress
        MessageCenter.AddMessage "Progress: [" & currentBoundaryNum & "/" & numBoundaries & "]"
        'Utils.updateProgress (progress)
        Set boundary = boundaries.item(o)
        'Get included property lines
        Dim oFence As Fence
        Dim oElem As Element
        Dim myView As View
        
        With ActiveSettings
            .FenceClip = False
            .FenceOverlap = True
        End With
    
        Set oFence = ActiveDesignFile.Fence
        oFence.Undefine
    
        Set myView = CommandState.LastView
    
        oFence.DefineFromElement myView, boundary
        oFence.Draw
        
        Dim fenceEE As ElementEnumerator
        Set fenceEE = oFence.GetContents(True)
        
        While fenceEE.MoveNext
            Dim propertyLine As Element
            '  ee.Current is returning a copy of the element
            '  because this program called GetContents with
            '  the CloneElements argument set to True.
            Set propertyLine = fenceEE.Current.Clone
            If propertyLine.IsLineElement And Not propertyLine.Level Is Nothing Then
                If propertyLine.Level.name = "Exist Property Line" And propertyLine.AsLineElement.length > minLength Then
                    'Is a line element
                    'Get length
                    Dim startPt As Point3d
                    startPt = propertyLine.AsLineElement.startPoint
                    Dim endPt As Point3d
                    endPt = propertyLine.AsLineElement.endPoint
                    'Check if it intersects the boundary
                    Dim intersections() As Point3d
                    intersections = propertyLine.AsLineElement.GetIntersectionPoints(boundary, Matrix3dIdentity)
                    If UBound(intersections) <> -1 Then
                        'Has intersection
                        'iterate through intersections
                        For i = 0 To UBound(intersections)
                            'Find the side that is inside the boundary
                            Dim pointBefore As Point3d
                            Dim beforeDistance As Double
                            beforeDistance = propertyLine.AsLineElement.DistanceAtPoint(intersections(i)) - 1
                            If beforeDistance > 0 Then
                                pointBefore = propertyLine.AsLineElement.PointAtDistance(beforeDistance)
                                'pointAfter = propertyLine.AsLineElement.PointAtDistance(propertyLine.AsLineElement.DistanceAtPoint(intersections(i) + 1))
                                If inside(boundary, pointBefore) Then
                                    'Change last vertex
                                    propertyLine.AsLineElement.ModifyVertex propertyLine.AsLineElement.VerticesCount - 1, intersections(i)
                                Else
                                    'Change first vertex
                                    propertyLine.AsLineElement.ModifyVertex 0, intersections(i)
                                End If
                            End If
                        Next i
                    End If
                    'Find open spot
                    Dim currentSpot As Double
                    currentSpot = propertyLine.AsLineElement.length / 2
                    Dim centerDistance As Double
                    centerDistance = 0
                    Dim direction As Integer
                    direction = 1
                    Do
                        If isOpen(propertyLine, currentSpot + centerDistance * direction) Then
                            'Found Spot
                            currentSpot = currentSpot + centerDistance * direction
                            Exit Do
                        Else
                            centerDistance = centerDistance + 10
                            direction = direction * -1
                        End If
                    Loop While centerDistance < propertyLine.AsLineElement.length / 2
                    'Place dimension
                    Dim centerPos As Point3d
                    centerPos = propertyLine.AsLineElement.PointAtDistance(currentSpot)
                    Dim dimensionElement As dimensionElement
                    Dim myView1 As View
                    Set myView1 = CommandState.LastView
                    'getRotationMatrix(Vector3dSubtractPoint3dPoint3d(startpt, endpt), Vector3dFromXY(1, 0))
                    Set dimensionElement = CreateDimensionElement1(Nothing, Matrix3dIdentity, msdDimTypeLabelLine, myView1)
                    dimensionElement.AddReferencePoint ActiveModelReference, startPt
                    dimensionElement.AddReferencePoint ActiveModelReference, endPt
                    Dim moveDistance As Point3d
                    moveDistance = Point3dSubtract(centerPos, startPt)
                    dimensionElement.Move moveDistance
                    dimensionElement.Color = 5
                    dimensionElement.LineWeight = 1
                    
                    dimensionElement.Level = ActiveModelReference.Levels("Exist Property Line Text")
                    dimensionElement.LineStyle = ActiveModelReference.Levels("Exist Property Line Text").ElementLineStyle
                    'Add element
                    ActiveModelReference.AddElement dimensionElement
                    dimensionElement.Rewrite
                    dimensionElement.Redraw
                    Debug.Print "Added element"
                End If
            End If
        Wend
    Next o
    'Utils.closeProgress
End Function

Private Function isOpen(line As LineElement, spot As Double) As Boolean
    Dim oFence As Fence
    Dim oElem As Element
    Dim myView As View
    
    With ActiveSettings
        .FenceClip = False
        .FenceOverlap = True
    End With

    Set oFence = ActiveDesignFile.Fence
    oFence.Undefine

    Set myView = CommandState.LastView
    
    Dim boundary As ShapeElement
    Dim verticies(0 To 3) As Point3d
    Dim parallel As Vector3d
    Dim perpendicular As Vector3d
    Dim center As Point3d
    center = line.PointAtDistance(spot)
    parallel = Vector3dNormalize(Vector3dSubtractPoint3dPoint3d(line.startPoint, line.endPoint))
    perpendicular = Vector3dUnitPerpendicularXY(parallel)
    verticies(0) = Point3dAdd2ScaledVector3d(center, parallel, 15, perpendicular, 7)
    verticies(1) = Point3dAdd2ScaledVector3d(center, parallel, -15, perpendicular, 7)
    verticies(2) = Point3dAdd2ScaledVector3d(center, parallel, -15, perpendicular, -7)
    verticies(3) = Point3dAdd2ScaledVector3d(center, parallel, 15, perpendicular, -7)
    Set boundary = CreateShapeElement1(Nothing, verticies, msdFillModeNotFilled)
    
    oFence.DefineFromElement myView, boundary
    oFence.Draw
    
    Dim fenceEE As ElementEnumerator
    Set fenceEE = oFence.GetContents(True)
    
    Dim valid As Boolean
    valid = True
    Do While fenceEE.MoveNext
        Set oElem = fenceEE.Current
        If Not oElem.Level Is Nothing Then
            If oElem.Level.name = "Exist Property Line" Then
                'Property Line
            ElseIf oElem.Level.name = "Level 63" Then
                'Map boundary
            ElseIf oElem.Level.name = "Level 62" Then
                'Map Number
            Else
                valid = False
            End If
        Else
            valid = False
        End If
        If Not valid Then Exit Do
    Loop

    isOpen = valid
End Function

Private Function inside(boundary As ComplexShapeElement, point As Point3d) As Boolean

    Dim verticies(5) As Point3d
    Dim ee As ElementEnumerator
    Set ee = boundary.GetSubElements
    For i = 0 To 3
        ee.MoveNext
        verticies(i) = ee.Current.AsLineElement.startPoint
    Next i
    verticies(4) = verticies(0)
    
    Dim xMax As Double
    Dim xMin As Double
    Dim yMax As Double
    Dim yMin As Double
    xMax = verticies(0).x
    xMin = verticies(0).x
    yMax = verticies(0).y
    yMin = verticies(0).y
    If xMax = 0 Then
        Debug.Print "0 point should not be 0"
    End If
    For i = 1 To UBound(verticies)
        If verticies(i).x <> 0 Then
            If verticies(i).x > xMax Then
                xMax = verticies(i).x
            End If
            If verticies(i).x < xMin Then
                xMin = verticies(i).x
            End If
            If verticies(i).y > yMax Then
                yMax = verticies(i).y
            End If
            If verticies(i).y < yMin Then
                yMin = verticies(i).y
            End If
        End If
    Next i
    Const variability As Double = 0.01
    If point.x + variability >= xMin And point.x - variability <= xMax And point.y + variability >= yMin And point.y - variability <= yMax Then
        inside = True
    Else
        inside = False
    End If
End Function

Function getRotationMatrix(v1 As Vector3d, v2 As Vector3d) As Matrix3d
    Dim theta As Double
    theta = Vector3dAngleBetweenVectorsXY(v1, v2)
    Dim Axis As Point3d
    Axis.x = 0
    Axis.y = 0
    Axis.Z = 1
    getRotationMatrix = Matrix3dFromVectorAndRotationAngle(Axis, theta * -1)
End Function

Attribute VB_Name = "RWModule"
Function AddAllRWDimensions()
    Debug.Print "R/W Dimension Start"
    Dim ee As ElementEnumerator
    If Not ActiveDesignFile.Fence.IsDefined Then
        If ActiveModelReference.AnyElementsSelected Then
            Set ee = ActiveModelReference.GetSelectedElements()
        Else
            MsgBox "Fence is not defined"
            Exit Function
        End If
    Else
        With ActiveSettings
        .FenceClip = False
        .FenceOverlap = True
    End With
    
    Set ee = ActiveDesignFile.Fence.GetContents(True)
    End If
    
    'Get Templates
    Dim textTemplate As TextElement
    Dim dimensionTemplate As dimensionElement
    Set textTemplate = getTextTemplate()
    Set dimensionTemplate = getDimensionTemplate()
    Dim oElem As Element
    Dim minDistance As Double
    While ee.MoveNext
        Set oElem = ee.Current
        minDistance = CDbl(AutoBoreForm.MinEOPDistance)
        If oElem.IsTextElement Then
            If (Point3dDistance(oElem.Range.high, oElem.Range.low) / 2) > minDistance Then minDistance = (Point3dDistance(oElem.Range.high, oElem.Range.low) / 2) + 10
            If oElem.Level.name = "Exist Roads EOP Text" And InStr(oElem.AsTextElement.text, " ") <> 0 Then
                AddDimension oElem.AsTextElement.origin, dimensionTemplate, textTemplate, minDistance
            End If
        ElseIf oElem.IsTextNodeElement Then
            If (Point3dDistance(oElem.Range.high, oElem.Range.low) / 2) > minDistance Then minDistance = (Point3dDistance(oElem.Range.high, oElem.Range.low) / 2) + 10
            If oElem.Level.name = "Exist Roads EOP Text" And InStr(oElem.AsTextNodeElement.TextLine(1), " ") <> 0 Then
                AddDimension oElem.AsTextNodeElement.origin, dimensionTemplate, textTemplate, minDistance
            End If
        End If
    Wend
    
    ActiveDesignFile.Fence.Undefine
    MsgBox "Completed"
End Function

Function AddDimension(roadName As Point3d, dimensionTemplate As dimensionElement, textTemplate As TextElement, minDistance As Double)
    Dim maxRW As Double
    maxRW = CDbl(AutoBoreForm.MaxRWDistance)
    Dim nearby As Collection
    Set nearby = Utils.NearbyElements(roadName, maxRW)
    
    Dim closest1 As Double
    Dim closest2 As Double
    closest1 = -1
    closest2 = -1
    Dim p1 As Point3d
    Dim p2 As Point3d
    Dim oElem As Element
    Dim rwElem As ChainableElement
    Dim rwElem2 As IntersectableElement
    
    Dim currDistance As Double
    Dim currPoint As Point3d
    For i = 1 To nearby.count
        Set oElem = nearby.item(i)
        If oElem.IsChainableElement And oElem.IsIntersectableElement Then
            If Not oElem.Level Is Nothing Then
                If oElem.Level.name = "Exist Right of Way Line" Then
                    currPoint = oElem.AsIntersectableElement.ProjectPointOnPerpendicular2(roadName, Matrix3dIdentity)
                    currDistance = Point3dDistance(currPoint, roadName)
                    If currDistance < closest1 Or closest1 = -1 Then
                        If closest1 <> -1 Then
                            If Not areLinesConnected(oElem, rwElem) Then
                                closest2 = closest1
                                Set rwElem2 = rwElem
                            End If
                        End If
                        
                        Set rwElem = oElem
                        closest1 = currDistance
                        p1 = currPoint
                    ElseIf currDistance < closest2 Or closest2 = -1 Then
                        If Not areLinesConnected(rwElem, oElem) Then
                            closest2 = currDistance
                            Set rwElem2 = oElem
                        End If
                    End If
                End If
            End If
        End If
    Next i
    If closest1 = -1 Or closest2 = -1 Then
        Debug.Print "No R/W near: " & roadName.x & " " & roadName.y
        Exit Function
    End If
    p2 = rwElem2.ProjectPointOnPerpendicular2(p1, Matrix3dIdentity)
    'Move down the element a bit
    Dim moveDistance As Double
    moveDistance = minDistance
    Dim maxDistance As Double
    maxDistance = CDbl(AutoBoreForm.MaxEOPDistance)
    Dim direction As Integer
    Dim originalLength As Double
    originalLength = Point3dDistance(p1, p2)
    direction = 1
    currDistance = rwElem.DistanceAtPoint(p1)
    Dim moveDir As Point3d
    Dim checkDistance As Double
    Dim checkP1 As Point3d
    Dim checkP2 As Point3d
    Do
        checkDistance = currDistance + (moveDistance * direction)
        If checkDistance > rwElem.length Or checkDistance < 0 Or moveDistance > maxDistance Then
            Exit Do
        End If
        
        currPoint = rwElem.PointAtDistance(checkDistance)
        moveDir = Point3dSubtract(currPoint, p1)
        checkP1 = Point3dAdd(p1, moveDir)
        checkP2 = rwElem2.ProjectPointOnPerpendicular2(checkP1, Matrix3dIdentity)
        
        If Abs(originalLength - Point3dDistance(checkP1, checkP2)) < 1 And isClear(checkP1, checkP2) Then
            p1 = checkP1
            p2 = checkP2
            Exit Do
        End If
        
        direction = direction * -1
        moveDistance = moveDistance + 5
    Loop
    
    AddDimensionFromPoints p1, p2, dimensionTemplate, textTemplate
End Function

Function areLinesConnected(line1 As ChainableElement, line2 As ChainableElement) As Boolean
    areLinesConnected = Point3dDistance(line1.startPoint, line2.startPoint) < 0.1 Or Point3dDistance(line1.endPoint, line2.startPoint) < 0.1 Or Point3dDistance(line1.startPoint, line2.endPoint) < 0.1 Or Point3dDistance(line1.endPoint, line2.endPoint) < 0.1
End Function

Function isClear(point1 As Point3d, point2 As Point3d) As Boolean
    Dim p2Top1 As Point3d
    p2Top1 = Point3dScale(Point3dNormalize(Point3dSubtract(point1, point2)), 8)
    Dim p1ToCorner As Point3d
    p1ToCorner = Point3dScale(Point3dNormalize(Point3dRotateXY(p2Top1, 1.5707)), 20)
    ' Create search shape
    Dim searchBox As ShapeElement
    Dim verticies(0 To 4) As Point3d
    verticies(0) = Point3dAdd(point1, p1ToCorner)
    verticies(1) = Point3dAdd(verticies(0), p2Top1)
    verticies(2) = Point3dAdd(verticies(1), Point3dScale(p1ToCorner, -2))
    verticies(3) = Point3dSubtract(verticies(2), p2Top1)
    verticies(4) = verticies(0)
    Set searchBox = CreateShapeElement1(Nothing, verticies)
    
    If Not isShapeClear(searchBox) Then
        isClear = False
        Exit Function
    End If
    
    verticies(0) = Point3dAdd(point2, p1ToCorner)
    verticies(1) = Point3dSubtract(verticies(0), p2Top1)
    verticies(2) = Point3dAdd(verticies(1), Point3dScale(p1ToCorner, -2))
    verticies(3) = Point3dAdd(verticies(2), p2Top1)
    verticies(4) = verticies(0)
    Set searchBox = CreateShapeElement1(Nothing, verticies)
    
    isClear = isShapeClear(searchBox)
End Function

Function isShapeClear(shape As ShapeElement) As Boolean
    Dim oFence As Fence
    Dim oElem As Element
    Dim myView As View
    
     With ActiveSettings
        .FenceClip = False
        .FenceOverlap = True
    End With

    Set oFence = ActiveDesignFile.Fence
    oFence.Undefine

    Set myView = CommandState.LastView

    oFence.DefineFromElement myView, shape
    'Is this needed?
    oFence.Draw
    'Debug.Print "View: " & oFence.
    'See CopyFenceContents() example to possible implement saving the active settings (probably should do outside this method)
    Dim ee As ElementEnumerator
    Set ee = oFence.GetContents(False)
    Dim good As Boolean
    While ee.MoveNext
        good = False
        Set oElem = ee.Current
        If Not oElem.Level Is Nothing Then
            If oElem.Level.name = "Exist Right of Way Line" Or oElem.Level.name = "Level 63" Or oElem.Level.name = "Level 62" Then good = True
        End If
        If Not good Then
            isShapeClear = False
            Exit Function
        End If
    Wend
    isShapeClear = True
End Function

Function AddDimensionFromPoints(p1 As Point3d, p2 As Point3d, dimensionTemplate As dimensionElement, textTemplate As TextElement)
    Dim p2Top1 As Vector3d
    p2Top1 = Vector3dSubtractPoint3dPoint3d(p1, p2)
    
    'Dimension Element
    Dim dimEle As dimensionElement
    Set dimEle = CreateDimensionElement1(dimensionTemplate, Utils.getRotationMatrix(p2Top1, Vector3dFromXY(1, 0)), msdDimTypeCustomLinear)
    dimEle.AddReferencePoint ActiveModelReference, p1
    dimEle.AddReferencePoint ActiveModelReference, p2
    dimEle.Level = ActiveModelReference.Levels("Exist Right of Way Width CELL")
    dimEle.Color = ByLevelColor
    dimEle.LineStyle = ByLevelLineStyle
    dimEle.LineWeight = ByLevelLineWeight
    ActiveModelReference.AddElement dimEle
    dimEle.Redraw
    
    'Labels
    Dim labelRotation As Matrix3d
    labelRotation = Utils.getRotationMatrix(p2Top1, Vector3dFromXY(0, 1))
    Dim textp1 As Point3d
    If labelRotation.RowY.y < 0 Then
        textp1 = Point3dAddPoint3dVector3d(p1, Vector3dScale(Vector3dNormalize(p2Top1), 8))
    Else
        textp1 = Point3dAddPoint3dVector3d(p1, Vector3dScale(Vector3dNormalize(p2Top1), 1))
    End If
    
    Dim label As TextElement
    Set label = CreateTextElement1(textTemplate, "EXISTING R/W", textp1, labelRotation)
    label.Level = ActiveModelReference.Levels("Exist Right of Way Line Text")
    label.Color = ByLevelColor
    label.LineStyle = ByLevelLineStyle
    label.LineWeight = ByLevelLineWeight
    If labelRotation.RowY.y < 0 Then
        label.RotateAboutZ label.origin, 3.14159
    End If
    
    label.TextStyle = ActiveDesignFile.TextStyles("R/W Offset")
    ActiveModelReference.AddElement label
    label.Rewrite
    label.Redraw
    
    Dim textp2 As Point3d
    If labelRotation.RowY.y < 0 Then
        textp2 = Point3dAddPoint3dVector3d(p2, Vector3dScale(Vector3dNormalize(p2Top1), -4))
    Else
        textp2 = Point3dAddPoint3dVector3d(p2, Vector3dScale(Vector3dNormalize(p2Top1), -8))
    End If
    Set label = CreateTextElement1(textTemplate, "EXISTING R/W", textp2, labelRotation)
    label.Level = ActiveModelReference.Levels("Exist Right of Way Line Text")
    label.TextStyle = ActiveDesignFile.TextStyles("R/W Offset")
    label.Color = ByLevelColor
    label.LineStyle = ByLevelLineStyle
    label.LineWeight = ByLevelLineWeight
    If labelRotation.RowY.y < 0 Then
        label.RotateAboutZ label.origin, 3.14159
    End If
    ActiveModelReference.AddElement label
    label.Rewrite
    label.Redraw

End Function

Function getDimensionTemplate() As dimensionElement
    Dim ee As ElementEnumerator
    Dim oScanCriteria As ElementScanCriteria
    Dim dimEle As dimensionElement
    Set oScanCriteria = New ElementScanCriteria
    oScanCriteria.ExcludeAllTypes
    oScanCriteria.IncludeType msdElementTypeDimension
    oScanCriteria.ExcludeAllLevels
    oScanCriteria.IncludeLevel ActiveModelReference.Levels("Exist Right of Way Width CELL")
    Set ee = ActiveModelReference.Scan(oScanCriteria)
    If ee.MoveNext Then Set dimEle = ee.Current
    
    Set getDimensionTemplate = dimEle
End Function

Function getTextTemplate() As TextElement
    Dim ee As ElementEnumerator
    Dim oScanCriteria As ElementScanCriteria
    Dim textEle As TextElement
    Set oScanCriteria = New ElementScanCriteria
    oScanCriteria.ExcludeAllTypes
    oScanCriteria.IncludeType msdElementTypeText
    oScanCriteria.ExcludeAllLevels
    oScanCriteria.IncludeLevel ActiveModelReference.Levels("Exist Right of Way Line Text")
    Set ee = ActiveModelReference.Scan(oScanCriteria)
    If ee.MoveNext Then Set textEle = ee.Current
    
    Set getTextTemplate = textEle
End Function

Attribute VB_Name = "ReferencedActionPoint"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private point_reference As Long
Private point_distance As Double

Property Get PointReference() As Long
    PointReference = point_reference
End Property

Property Get PointDistance() As Double
    PointDistance = point_distance
End Property

Property Let PointReference(pType As Long)
    point_reference = pType
End Property

Property Let PointDistance(pDistance As Double)
    point_distance = pDistance
End Property

Private Sub Class_Initialize()
    point_distance = 0
    point_reference = 0
End Sub

Attribute VB_Name = "RoadsModule"
'Formats the SR numbers in the road names to have a dash and 2 spaces afterwards
Function FormatSRNumbers()
    Debug.Print "Formatting Road Names"
    Dim oScanCriteria As ElementScanCriteria
    Set oScanCriteria = New ElementScanCriteria
    oScanCriteria.ExcludeAllTypes
    oScanCriteria.ExcludeAllLevels
    oScanCriteria.IncludeLevel ActiveModelReference.Levels("Exist Roads EOP Text")
    oScanCriteria.IncludeType msdElementTypeText
    oScanCriteria.IncludeType msdElementTypeTextNode
    Dim ee As ElementEnumerator
    Set ee = ActiveModelReference.Scan(oScanCriteria)
    Dim oElem As Element
    Dim content As String
    Dim count As Long
    count = 0
    While ee.MoveNext
        Set oElem = ee.Current
        If oElem.IsTextNodeElement Then
            content = oElem.AsTextNodeElement.TextLine(1)
        Else
            content = oElem.AsTextElement.text
        End If
        If InStr(content, "SR") = 1 Or InStr(content, "NC") = 1 Or InStr(content, "US") = 1 Then
            count = count + 1
            'Starts with SR, NC or US
            'Check if third character is a dash
            If InStr(content, "-") <> 3 Then
                If InStr(content, " ") = 3 Then
                    'Space instead of dash
                    content = Left(content, 2) & "-" & Right(content, Len(content) - 3)
                Else
                    'No Space
                    content = Left(content, 2) & "-" & Right(content, Len(content) - 2)
                End If
            End If
            'Check for double space
            Dim spaceIndex As Integer
            spaceIndex = InStr(content, " ")
            If mid(content, spaceIndex + 1, 1) <> " " Then
                'Add extra space
                content = Left(content, spaceIndex) & " " & Right(content, Len(content) - spaceIndex)
            End If
            'Check for ending double space before road width
            Dim number As Integer
            number = -1
            For i = spaceIndex + 1 To Len(content)
                On Error Resume Next
                number = CInt(mid(content, i, 1))
                If number <> -1 Then
                    'Found road width
                    If mid(content, i - 2, 1) <> " " Then
                        'Add space
                        content = Left(content, i - 1) & " " & Right(content, Len(content) - (i - 1))
                    End If
                    Exit For
                End If
            Next i
            'Update text
            If oElem.IsTextNodeElement Then
                oElem.AsTextNodeElement.TextLine(1) = content
            Else
                oElem.AsTextElement.text = content
            End If
            oElem.Color = 4
            oElem.LineWeight = 1
            oElem.Redraw
            oElem.Rewrite
        End If
    Wend
    Debug.Print "Formatted " & count & " road names."
End Function

Attribute VB_Name = "SmartAutoBore"

Function BreakBoreLine(mainLine As ComplexStringElement, switches As IntersectionList, roadNames As Collection)
    
    Dim referenceLine As ComplexStringElement
    Set referenceLine = mainLine.Clone
    Dim dimensioned As Double
    Dim point As Point3d
    Dim edge As Point3d
    Dim direction As Vector3d
    Dim firstInterestPoint As IntersectionPoint
    Dim secondInterestPoint As IntersectionPoint
    
    ' Format End Point
    switches.Add FormatBoreLineEnd(referenceLine, referenceLine.length)
    ' Format start point (add hand hole if needed
    Set secondInterestPoint = FormatBoreLineEnd(referenceLine, 0)
    switches.Add secondInterestPoint, 0 ' Add interest point to switch list for reference in dimensioning
    
    ' Break main line into segments with switch list
    Dim i As Long
    Dim secondInterestDistance As Double ' Distance at the start of the second interest point
    secondInterestDistance = 0
    Dim handHole As Element
    Dim prevLine As ComplexStringElement
    For i = 1 To switches.size - 1
        If mainLine Is Nothing Then
            Debug.Print "Ran out of length when cutting bore line!"
            Exit For
        End If
        Set firstInterestPoint = secondInterestPoint
        Set secondInterestPoint = switches.At(i)
        If firstInterestPoint.PointType = "PLOW" Or firstInterestPoint.PointType = "BORE" Then
            'Add length to secondInterestDistance
            secondInterestDistance = secondInterestDistance + firstInterestPoint.PointDistance
        End If
        
        ' Get point at the handhole
        If secondInterestDistance >= referenceLine.length Then
            point = referenceLine.endPoint
        Else
            point = referenceLine.PointAtDistance(secondInterestDistance)
        End If
        ' Get another point along the line
        If secondInterestPoint.isPit() Then
            If secondInterestPoint.EnterPoint Then
                edge = referenceLine.PointAtDistance(secondInterestDistance - 2.3)
            Else
                ' Exit point of something (road), use other side of line
                edge = referenceLine.PointAtDistance(secondInterestDistance + 2.3)
            End If
        End If
        
        If secondInterestPoint.PointType = "HANDHOLE" Then
            ' Add hand hole
            If i = switches.size - 1 Then
                ' Don't place hand hole at the end (already placed a little further)
                Set handHole = Nothing
            Else
                Set handHole = AutoBoreModule.PlaceHandHole(point, edge)
            End If
            ' Dimension element
            DimensionSegment CutLine(mainLine, referenceLine, point, firstInterestPoint.PointType = "BORE", handHole), i - 1, switches, roadNames
        ElseIf secondInterestPoint.PointType = "BOREPIT" Then
            If i <> switches.size - 1 Then
                ' Skip the last index, cuz that was already placed
                AutoBoreModule.PlaceBorePit point, edge
            End If
            
            ' Dimension element
            DimensionSegment CutLine(mainLine, referenceLine, point, firstInterestPoint.PointType = "BORE", Nothing), i - 1, switches, roadNames
        ElseIf (secondInterestPoint.PointType = "PLOW" And firstInterestPoint.PointType = "PLOW") Or (secondInterestPoint.PointType = "BORE" And firstInterestPoint.PointType = "BORE") Then
            ' Dimension element continuation
            DimensionSegment CutLine(mainLine, referenceLine, point, firstInterestPoint.PointType = "BORE", Nothing), i - 1, switches, roadNames
        ElseIf (secondInterestPoint.PointType = "PLOW" And firstInterestPoint.PointType = "BORE") Or (secondInterestPoint.PointType = "BORE" And firstInterestPoint.PointType = "PLOW") Then
            MsgBox "Invalid transition between bore and plow without a bore pit or handhole!" & vbNewLine & point.x & ", " & point.y, vbExclamation, "Warning"
            Debug.Print "Invalid transition between bore and plow without a bore pit or handhole! " & point.x & ", " & point.y
        End If
        ' Else transitioning from bore pit/hh to plow/bore
        
            
    Next i
    
End Function

' Create the dimension text node for a bore line.
'
' @param segmentElement     The element being dimensioned.
' @param segmentIndex       The index of the segment in the switch list
' @param switches           The switch list of bore segments and bore pits.
' @param roadNames          A collection of road names and their location along the bore line
Function DimensionSegment(segmentElement As ChainableElement, segmentIndex As Long, switches As IntersectionList, roadNames As Collection)
    If segmentElement Is Nothing Then Exit Function
    If segmentElement.length < 6 Then Exit Function
    ' use segmentElement length
    Dim dimension As Double
    dimension = segmentElement.length + switches.At(segmentIndex + 1).GetDimensionLength() + switches.At(segmentIndex - 1).GetDimensionLength()
    Dim dimensionedString As String
    dimensionedString = CStr(Int((dimension + 5) / 5) * 5)
    Dim roadName As String
    roadName = AutoBoreModule.GetNearestRoad(getSegmentStartingPoint(segmentIndex, switches) + (switches.At(segmentIndex).PointDistance / 2), roadNames)
    Dim dimensionedElement As TextNodeElement
    Dim center As Point3d
    center = segmentElement.PointAtDistance(segmentElement.length / 2)
    If switches.At(segmentIndex).PointType = "PLOW" Then
        Set dimensionedElement = Utils.CreateBoreDimension(center, dimensionedString, roadName, 0)
    Else
        If switches.At(segmentIndex + 1).EnterPoint Then ' this will be false for a road crossing
            Set dimensionedElement = Utils.CreateBoreDimension(center, dimensionedString, roadName, 1)
        Else
            Set dimensionedElement = Utils.CreateBoreDimension(center, dimensionedString, roadName, 2)
        End If
    End If
    
    ActiveModelReference.AddElement dimensionedElement
    dimensionedElement.Redraw
End Function

' Format the end of the bore line
'
' @param referenceLine  The bore line element
' @param distance       The distance along the bore line element to format. Expected to be 0 or referenceLine.length
' @returns              The intersection point at this end of the line
Function FormatBoreLineEnd(referenceLine As ComplexStringElement, distance As Double) As IntersectionPoint
    Dim secondInterestPoint As IntersectionPoint
    Dim handHolePresence As Integer
    Dim point As Point3d
    Dim edge As Point3d
    Dim direction As Point3d
    If distance > 0 Then
        point = referenceLine.endPoint
    Else
        point = referenceLine.startPoint
    End If
    'point = referenceLine.PointAtDistance(distance)
    
    handHolePresence = ShouldAddHandHole(point, 10)
    If handHolePresence = -1 Then
        ' Nothing found add hand hole
        If distance - 2.3 > 0 Then
            edge = referenceLine.PointAtDistance(distance - 2.3)
        Else
            edge = referenceLine.PointAtDistance(distance + 2.3)
        End If
        'Move points towards the end to fit handhole w/o breaking the line
        direction = Point3dScale(Point3dNormalize(Point3dSubtract(edge, point)), (5.725 / 2))
        point = Point3dSubtract(point, direction)
        edge = Point3dSubtract(edge, direction)
        AutoBoreModule.PlaceHandHole point, edge
        Set secondInterestPoint = CreateIntersectionPoint(distance, "HANDHOLE")
    ElseIf handHolePresence = 1 Then
        ' Bore pit at the start
        Set secondInterestPoint = CreateIntersectionPoint(distance, "BOREPIT")
    ElseIf handHolePresence = 2 Then
        ' Hand hole at the start
        Set secondInterestPoint = CreateIntersectionPoint(distance, "HANDHOLE")
    Else
        ' Other lines nearby
        Set secondInterestPoint = CreateIntersectionPoint(0, "PLOW")
    End If
        Set FormatBoreLineEnd = secondInterestPoint
End Function

' Cut the bore line at a point
'
' @param mainLine       The bore line to cut. Will be updated with the new line after.
' @param referenceLine  The bore line before any cuts were preformed. This is used to get a point from the cutPoint distance
' @param cutPoint       The point along the bore line that should be cut
' @param trimElement    The element to trim the bore line to when the cut is complete. Can be Nothing
Function CutLine(ByRef mainLine As ComplexStringElement, referenceLine As ComplexStringElement, point As Point3d, bore As Boolean, trimElement As Element) As ComplexStringElement
    Dim beforeLine As ComplexStringElement
    Dim afterLine As ComplexStringElement
    ' Break mainLine at point
    mainLine.PartialDelete beforeLine, afterLine, point, point, point, 1
    'Remove previous line
    ActiveModelReference.RemoveElement mainLine
    
    If Not trimElement Is Nothing Then
        ' Trim lines
        If Not beforeLine Is Nothing Then TrimLineToElement beforeLine, trimElement, point
        If Not afterLine Is Nothing Then TrimLineToElement afterLine, trimElement, point
    End If
    
    If Not beforeLine Is Nothing Then
        If bore Then
            Set beforeLine.LineStyle = ActiveDesignFile.LineStyles("0")
        Else
            Set beforeLine.LineStyle = ActiveDesignFile.LineStyles("2")
        End If
        
        ActiveModelReference.AddElement beforeLine
        beforeLine.Redraw msdDrawingModeNormal
        beforeLine.Rewrite
    End If
    
    If Not afterLine Is Nothing Then
        ActiveModelReference.AddElement afterLine
        afterLine.Redraw
    End If
    
    Set mainLine = afterLine
    Set CutLine = beforeLine
End Function

' Trim a bore line around an element
'
' @param boreLine       The line to trim
' @param trimElement    The element to trim the line to
' @param point          The start or end point of the boreline that deisgnates the new element to remove
Function TrimLineToElement(ByRef boreLine As ComplexStringElement, trimElement As Element, point As Point3d)
    Dim intersections() As Point3d
    Dim iPoint As Point3d
    Dim bLine As ComplexStringElement
    Dim aLine As ComplexStringElement
    If trimElement.IsCellElement Then
        Dim ee As ElementEnumerator
        Set ee = trimElement.AsCellElement.GetSubElements()
        While ee.MoveNext
            intersections = boreLine.AsIntersectableElement.GetIntersectionPoints(ee.Current, Matrix3dIdentity)
            If UBound(intersections) <> -1 Then
                For i = 0 To UBound(intersections)
                    ' Cut element at intersection point
                    boreLine.PartialDelete bLine, aLine, intersections(i), intersections(i), intersections(i), 1
                    ' Find which element should be the saved line
                    If Not bLine Is Nothing Then
                        If aLine Is Nothing Then
                            Set boreLine = bLine
                        ElseIf CompareCloser(bLine, aLine, point) Then
                            Set boreLine = aLine
                        Else
                            Set boreLine = bLine
                        End If
                    End If
                Next i
            End If
        Wend
    Else
        ' Add implimentation for elements other than cell element
    End If
End Function

' Checks if the closest line is closer than the furthest line to the point. Compares end points of the lines.
Function CompareCloser(closest As ComplexStringElement, furthest As ComplexStringElement, point As Point3d) As Boolean
    CompareCloser = Utils.Min(Point3dDistance(closest.startPoint, point), Point3dDistance(closest.endPoint, point)) < Utils.Min(Point3dDistance(furthest.startPoint, point), Point3dDistance(furthest.endPoint, point))
End Function


' Check if a hand hole should be added at a point. A hand hole should be added if there is less than 2 bore lines and there isn't a bore pit or hand hole already present
'
' @param origin     Location to add a hand hole
' @param radius     The distance around the location to search for other hand holes or bore lines. 10 feet is suggested
' @return           0 If there are more than 1 bore lines in the area
'                   1 If there is a bore pit in the area
'                   2 If there is a hand hole in the area
'                   -1 Otherwise (hand hole should be added)
Function ShouldAddHandHole(origin As Point3d, radius As Double) As Integer
    Dim nearby As Collection
    Set nearby = Utils.NearbyElements(origin, radius)
    Dim boreLineFound As Integer
    boreLineFound = 0
    Dim borePitFound As Boolean
    borePitFound = False
    Dim handHoleFound As Boolean
    handHoleFound = False
    Dim ele As Element
    For i = 1 To nearby.count
        Set ele = nearby.item(i)
        If Not ele.Level Is Nothing Then
            If ele.IsComplexStringElement And ele.Level.name = "Level 30" Then
                ' Bore line
                boreLineFound = boreLineFound + 1
            ElseIf IsBorePit(ele) Then
                borePitFound = True
            ElseIf ele.IsCellElement Then
                If ele.AsCellElement.name = "EXIST UTILITIES TELEPHONE HAND HOLE" Then
                    'Hand hole
                    handHoleFound = True
                End If
            End If
        ElseIf ele.IsCellElement Then
            If ele.AsCellElement.name = "EXIST UTILITIES TELEPHONE HAND HOLE" Then
                'Hand hole
                handHoleFound = True
            End If
        End If
    Next i
    If handHoleFound Then
        ShouldAddHandHole = 2
    ElseIf borePitFound Then
        ShouldAddHandHole = 1
    ElseIf boreLineFound > 1 Then
        ShouldAddHandHole = 0
    Else
        ShouldAddHandHole = -1
    End If
End Function

' Check if an element is a bore pit. Sometimes microstation can glitch out and return an empty level name.
'
' @param oElem  Element to check
' @returns      true if the element is a bore pit.
Function IsBorePit(oElem As Element) As Boolean
    If Not oElem Is Nothing Then
     If oElem.IsComplexShapeElement And Not oElem.Level Is Nothing Then
        If oElem.Level.name = "Level 12" Or (oElem.Level.name = "" And oElem.AsComplexShapeElement.ApparentColor(CommandState.LastView) = 87 And oElem.AsComplexShapeElement.Area() < 20) Then
            IsBorePit = True
            Exit Function
        End If
     End If
    End If
    IsBorePit = False
End Function

' Create better switch list from intersection points
Function CreateBoreSegments(culvertIntersections As Collection, soilIntersections As Collection, poleIntersections As Collection, matchIntersections As Collection, roadIntersections As Collection, bridgeIntersections As Collection, drivewayIntersections As Collection, guardrailIntersections As Collection, lineLength As Double) As IntersectionList
    Dim i As Long
    ' Create IntersectionList
    Dim intersections As IntersectionList
    Set intersections = CreateIntersectionList(culvertIntersections, soilIntersections, poleIntersections, matchIntersections, roadIntersections, bridgeIntersections, drivewayIntersections, guardrailIntersections, lineLength)
    intersections.PrintPoints
    ' Create switch list (Assuming start and end are hand holes or a bore pit depending on what is in the project or if hand holes need to be added)
    Dim switches As New IntersectionList
    ' Grab form values
    Dim maxBoreConnection As Double
    maxBoreConnection = CDbl(AutoBoreForm.MaxBoreConnectionDistance)
    
    ' Start some bore pit calculations
    Dim intersectionPt As IntersectionPoint
    Dim prevIntersectionPt As IntersectionPoint
    Dim prevDistanceAfter As Double
    Dim distance As Double
    Dim lastBorePit As Double
    lastBorePit = 0
    Dim bore As Boolean
    bore = True
    ' Get first intersection
    Set intersectionPt = GetBoreIntersection(0, 1, intersections)
    
    If intersectionPt Is Nothing Then
        'No intersections throughout the whole line
        switches.Add CreateIntersectionPoint(intersections.At(intersections.size - 1).PointDistance, "PLOW")
    Else
    
        distance = GetPitLocation(intersectionPt, -1, intersections) ' Get position of first bore pit
        If ShouldSeparateIntersections(CreateIntersectionPoint(0, "START"), 0, intersectionPt, distance) Then
            ' First bore does not connect to beginning hand hole
            switches.Add CreateIntersectionPoint(distance, "PLOW")
            switches.Add CreateIntersectionPoint(distance, "BOREPIT")
            lastBorePit = distance
        End If
    
        ' Check Make connections for the rest of the line
        
        ' While iterating through this loop, the last element in switches will always be a bore pit starting a bore section
        Do While True
            ' swap prev intersection with curr intersection & grab new intersection
            Set prevIntersectionPt = intersectionPt
            
            prevDistanceAfter = GetPitLocation(prevIntersectionPt, 1, intersections) ' Get adjusted position of next pit after prev intersection
            
            ' Check if prev intersection was the start of a road crossing
            If prevIntersectionPt.PointType = "ROAD" And prevIntersectionPt.EnterPoint Then
                ' SPECIAL CASE: Road crossing
                Set intersectionPt = intersections.GetIntersection(prevIntersectionPt.PointDistance + 0.01, 1, "ROAD", False)
                
                Dim prevHandHole As Boolean ' Whether the previous intersection will get a hand hole
                prevHandHole = ChooseHandHoleRoadCrossing(prevIntersectionPt.PointDistance, intersectionPt.PointDistance, intersections)
                
                ' The last switch should be a bore pit for the start of the road intersection already
                If prevHandHole And prevIntersectionPt.PointDistance > 0 Then
                    ' Change last bore pit in switch list to hand hole
                    switches.SetIntersectionType switches.size - 1, "HANDHOLE"
                End If
                ' Add bore segment for between the road
                switches.Add CreateIntersectionPoint(intersectionPt.PointDistance - prevIntersectionPt.PointDistance, "BORE")
                ' Add next bore pit or hand hole if the first one isn't a hand hole
                 If prevHandHole Then
                    switches.Add CreateIntersectionPoint(intersectionPt.PointDistance, "BOREPIT", False)
                 ElseIf intersectionPt.PointDistance < lineLength Then
                    switches.Add CreateIntersectionPoint(intersectionPt.PointDistance, "HANDHOLE", False)
                 End If
                
                ' find next intersection after the exit road, and check if they should be combined, if so, continue on the while loop
                ' else, add plow segment and next bore pit, then continue in loop
                Set prevIntersectionPt = intersectionPt
                Set intersectionPt = GetBoreIntersection(prevIntersectionPt.PointDistance + 0.1, 1, intersections)
                If intersectionPt Is Nothing Then
                    ' End of Line, no more intersections after the last handhole
                    Set intersectionPt = intersections.At(intersections.size - 1)
                    If intersectionPt.PointDistance - prevIntersectionPt.PointDistance > 1 Then
                        ' Plow the rest of the line
                        switches.Add CreateIntersectionPoint(intersectionPt.PointDistance - prevIntersectionPt.PointDistance, "PLOW")
                    End If
                    Exit Do
                Else
                    distance = GetPitLocation(intersectionPt, -1, intersections)
                    If ShouldSeparateIntersections(prevIntersectionPt, prevIntersectionPt.PointDistance, intersectionPt, distance) Then
                        ' Add plow segment and bore pit
                        switches.Add CreateIntersectionPoint(distance - prevIntersectionPt.PointDistance, "PLOW")
                        switches.Add CreateIntersectionPoint(distance, "BOREPIT")
                    ElseIf intersectionPt.PointType = "ROAD" Then
                        ' This intersection is the start of a road, so a pit should be placed anyway
                        switches.Add CreateIntersectionPoint(distance - switches.At(switches.size - 1).PointDistance, "PLOW")
                        switches.Add CreateIntersectionPoint(distance, "BOREPIT") ' Add bore pit after prev intersection
                    End If
                End If
                
            Else
                ' Handle normal pit
                Set intersectionPt = GetBoreIntersection(prevIntersectionPt.PointDistance + 0.1, 1, intersections)
                If intersectionPt Is Nothing Then
                    ' Edge case: next bore intersection is Nothing = END OF LINE
                    ' Check if the intersection should connect with the end
                    Set intersectionPt = intersections.At(intersections.size - 1)
                    If ShouldSeparateIntersections(prevIntersectionPt, prevDistanceAfter, intersectionPt, intersectionPt.PointDistance) Then
                        ' Don't connect bore to the end of the line
                        switches.Add CreateIntersectionPoint(prevDistanceAfter - switches.At(switches.size - 1).PointDistance, "BORE") ' Add bore with length since last element (should be a bore pit)
                        switches.Add CreateIntersectionPoint(prevDistanceAfter, "BOREPIT") ' Add bore pit after prev intersection
                        switches.Add CreateIntersectionPoint(intersectionPt.PointDistance - prevDistanceAfter, "PLOW") ' Add plow section
                    Else
                        ' Connect bore to the end of the line
                        If switches.size = 0 Then
                            distance = intersectionPt.PointDistance
                        Else
                            distance = intersectionPt.PointDistance - switches.At(switches.size - 1).PointDistance
                        End If
                        switches.Add CreateIntersectionPoint(distance, "BORE") ' Add bore with length since last element (should be a bore pit)
                    End If
                    Exit Do
                End If
                
                ' check their distance between eachother to see if they combine (before or after extension)
                distance = GetPitLocation(intersectionPt, -1, intersections) ' Get adjusted position of next pit before intersection (where it would be if the intersections are too far away)
                
                If ShouldSeparateIntersections(prevIntersectionPt, prevDistanceAfter, intersectionPt, distance) Then
                    ' Intersections are too far apart to connect
                    ' add pit at prev extension point, add plow length, add next pit at curr extension point, continue in loop
                    ' Add bore with length since last element (should be a bore pit)
                    If switches.size = 0 Then
                        switches.Add CreateIntersectionPoint(prevDistanceAfter, "BORE")
                    Else
                        switches.Add CreateIntersectionPoint(prevDistanceAfter - switches.At(switches.size - 1).PointDistance, "BORE")
                    End If
                    switches.Add CreateIntersectionPoint(prevDistanceAfter, "BOREPIT") ' Add bore pit after prev intersection
                    switches.Add CreateIntersectionPoint(distance - prevDistanceAfter, "PLOW") ' Add plow section
                    switches.Add CreateIntersectionPoint(distance, "BOREPIT") ' Add bore pit at distance
                    lastBorePit = distance
                ElseIf intersectionPt.PointType = "ROAD" Then
                    ' This intersection is the start of a road, so a pit should be placed anyway
                    If switches.size = 0 Then
                        switches.Add CreateIntersectionPoint(distance, "BORE")
                    Else
                        switches.Add CreateIntersectionPoint(distance - switches.At(switches.size - 1).PointDistance, "BORE")
                    End If
                    switches.Add CreateIntersectionPoint(distance, "BOREPIT") ' Add bore pit after prev intersection
                End If
            End If
        Loop
    End If
    ' switches is formated with segments
    CheckSwitchList switches, intersections.At(intersections.size - 1).PointDistance
    
    ' add hand holes for bridges - TODO change new segments created into plow segments if there are no intersections inbetween the pits
    Set intersectionPt = intersections.GetIntersection(0, 1, "BRIDGE")
    Dim segmentIndex As Long
    If Not intersectionPt Is Nothing Then
        Do While Not intersectionPt Is Nothing
        segmentIndex = GetSegmentIndex(intersectionPt.PointDistance, switches)
            If intersectionPt.EnterPoint Then
                ' hand hole needs to go before this
                If segmentIndex <> 0 Then
                    Set prevIntersectionPt = switches.At(segmentIndex - 1) ' This is a bore pit or handHole cuz segmentIndex is for a segment
                    distance = ExtendPit(intersectionPt.PointDistance - intersectionPt.GetBoreRadius(), -1, intersections) ' point where the hand hole should go
                    If (intersectionPt.PointDistance - prevIntersectionPt.PointDistance < CDbl(AutoBoreForm.MaxBridgeHHDistance) And intersectionPt.PointDistance - prevIntersectionPt.PointDistance > intersectionPt.GetBoreRadius()) Or prevIntersectionPt.PointDistance > distance Then
                        ' bore pit/HH is close enough to bridge
                        If prevIntersectionPt.PointType = "BOREPIT" Then
                            ' Swap bore pit to hand hole here
                            switches.SetIntersectionType segmentIndex - 1, "HANDHOLE"
                        End If
                    Else
                        ' Need to add a hand hole
                        switches.Add CreateIntersectionPoint(prevIntersectionPt.PointDistance + switches.At(segmentIndex).PointDistance - distance, "BORE"), segmentIndex + 1
                        switches.SetIntersectionDistance segmentIndex, distance - prevIntersectionPt.PointDistance
                        switches.Add CreateIntersectionPoint(distance, "HANDHOLE"), segmentIndex + 1
                    End If
                End If
            Else
                ' hand hole needs to go after this
                If segmentIndex <> switches.size - 1 Then
                    Set prevIntersectionPt = switches.At(segmentIndex + 1) ' This is a bore pit or handHole
                    distance = ExtendPit(intersectionPt.PointDistance + intersectionPt.GetBoreRadius(), 1, intersections) ' point where the hand hole should go
                    If (prevIntersectionPt.PointDistance - intersectionPt.PointDistance < CDbl(AutoBoreForm.MaxBridgeHHDistance) And prevIntersectionPt.PointDistance - intersectionPt.PointDistance > intersectionPt.GetBoreRadius()) Or prevIntersectionPt.PointDistance < distance Then
                        ' bore pit/HH is close enough to bridge
                        If prevIntersectionPt.PointType = "BOREPIT" Then
                            ' Swap bore pit to hand hole here
                            switches.SetIntersectionType segmentIndex + 1, "HANDHOLE"
                        End If
                    Else
                        ' Need to add a hand hole
                        switches.Add CreateIntersectionPoint(prevIntersectionPt.PointDistance - distance, "BORE"), segmentIndex + 1
                        switches.SetIntersectionDistance segmentIndex, switches.At(segmentIndex).PointDistance - prevIntersectionPt.PointDistance + distance
                        switches.Add CreateIntersectionPoint(distance, "HANDHOLE"), segmentIndex + 1
                    End If
                End If
            End If
            
            Set intersectionPt = intersections.GetIntersection(intersectionPt.PointDistance + 0.1, 1, "BRIDGE")
        Loop
    End If
    
    ' Access hand holes

    If AutoBoreForm.AddAccessHandholes Then
        distance = 0
        Dim newHandholes As Collection
        Dim handholesToAdd As New Collection
        For i = 0 To switches.size
            If i = switches.size Then
                Set intersectionPt = CreateIntersectionPoint(intersections.At(intersections.size - 1).PointDistance, "HANDHOLE") ' handhole for the end point
            Else
                Set intersectionPt = switches.At(i)
            End If
            If intersectionPt.PointType = "HANDHOLE" Then
                Set newHandholes = GetAccessHandholes(i, distance, intersectionPt.PointDistance, switches, intersections)
                For j = 1 To newHandholes.count
                    handholesToAdd.Add newHandholes.item(j)
                Next j
                distance = intersectionPt.PointDistance
            End If
        Next i
        
        ' Add aquired handholes
        For i = 1 To handholesToAdd.count
            ' split line into 2 lines at each distance, and insert a handhole
            segmentIndex = GetSegmentIndex(handholesToAdd.item(i), switches)
            distance = getSegmentStartingPoint(segmentIndex, switches)
            switches.Add CreateIntersectionPoint(distance + switches.At(segmentIndex).PointDistance - handholesToAdd.item(i), switches.At(segmentIndex).PointType), segmentIndex + 1
            switches.SetIntersectionDistance segmentIndex, handholesToAdd.item(i) - distance
            switches.Add CreateIntersectionPoint(handholesToAdd.item(i), "HANDHOLE"), segmentIndex + 1
        Next i
    End If
    
    ' cut segments that intersect match lines, its now ok to break up the segment, pit, segment pattern
    Set intersectionPt = intersections.GetIntersection(0, 1, "MATCHLINE")
    If Not intersectionPt Is Nothing Then
        Do While Not intersectionPt Is Nothing
            segmentIndex = GetSegmentIndex(intersectionPt.PointDistance, switches)
            distance = getSegmentStartingPoint(segmentIndex, switches)
            switches.Add CreateIntersectionPoint(distance + switches.At(segmentIndex).PointDistance - intersectionPt.PointDistance, switches.At(segmentIndex).PointType), segmentIndex + 1
            switches.SetIntersectionDistance segmentIndex, intersectionPt.PointDistance - distance
            
            Set intersectionPt = intersections.GetIntersection(intersectionPt.PointDistance + 0.1, 1, "MATCHLINE")
        Loop
    End If
    
    CheckSwitchList switches, intersections.At(intersections.size - 1).PointDistance
    
    
    Set CreateBoreSegments = switches
    
End Function

Function CheckSwitchList(switches As IntersectionList, lineLength As Double)
    Dim distance As Double
    ' Check to make sure switches add up
    distance = 0
    Dim i As Long
    For i = 0 To switches.size - 1
        If switches.At(i).isPit() Then
            If Abs(distance - switches.At(i).PointDistance) > 0.00001 Then
                MsgBox "Calculated Pit location at index " & i & " does not match!", vbCritical, "Error"
                Debug.Print "Calculated Pit location at index " & i & " does not match!"
                Exit For
            End If
        Else
            distance = distance + switches.At(i).PointDistance
        End If
    Next i
    If Abs(distance - lineLength) > 0.00001 Then
        MsgBox "Calculated bore segments do not add up to line length!", vbCritical, "Error"
        switches.PrintPoints
        End
    End If
End Function

' Get distances at which access handholes should be added.
'
' @param distanceBefore     The distance along the bore line where a handhole is present. This is the begining of the area that needs access handholes.
' @param distanceAfter      The distance along the bore line where a handhole is present. This is the end of the area that needs access handholes.
' @param switches           The list of bore pits, handholes, and bore/plow segments
' @param intersections      The list of intersection points that could obstruct handhole placement.
' @returns                  A collection of doubles representing distances that hand holes should be added.
Function GetAccessHandholes(indexAfter As Long, distanceBefore As Double, distanceAfter As Double, switches As IntersectionList, intersections As IntersectionList) As Collection
    Dim newHandholes As New Collection
    Dim maximumAccessDistance As Double
    maximumAccessDistance = CDbl(AutoBoreForm.MaxAccessHandHoleDistance)
    Dim maximumAccessSnap As Double
    maximumAccessSnap = CDbl(AutoBoreForm.MaxAccessHandholeSnap)
    Dim centerPt As Double
    Dim keepLeft As Boolean
    'Debug.Print distanceAfter & " - " & distanceBefore & " = " & (distanceAfter - distanceBefore)
    If distanceAfter - distanceBefore < maximumAccessDistance Then
        ' base case
        Set GetAccessHandholes = newHandholes
        Exit Function
    ElseIf distanceAfter - distanceBefore < maximumAccessDistance * 2 Then
        ' Shorter segment, center should be in the middle
        centerPt = (distanceAfter + distanceBefore) / 2
        keepLeft = False
    ElseIf distanceAfter - distanceBefore < maximumAccessDistance * 3 Then
        ' Shorter segment
        centerPt = distanceBefore + ((distanceAfter - distanceBefore) / 3)
        keepLeft = False
    Else
        ' Extra Long segment, should try to get get close to maximumAccessDistance as possible w/o going over for one side
        centerPt = distanceBefore + maximumAccessDistance - 6 ' including the dimension for the hand holes
        keepLeft = True
    End If
    'Debug.Print "Center at " & centerPt & " Keepleft: " & keepLeft
    ' Look for any bore pits to snap to
    Dim closestIndex As Long
    closestIndex = -1
    Dim index As Long
    index = indexAfter - 1
    Do While index > 0
        If switches.At(index).PointType = "BOREPIT" Then
            If (Abs(switches.At(index).PointDistance - centerPt) < maximumAccessSnap And (Not keepLeft Or switches.At(index).PointDistance - distanceBefore < maximumAccessDistance)) _
            Or (switches.At(index).PointDistance - distanceBefore < maximumAccessDistance And distanceAfter - switches.At(index).PointDistance < maximumAccessDistance) Then
                ' bore pit within snap range (and not overbounds if keepleft) or both sides of the pit are close enough to another handhole
                If closestIndex = -1 Then
                    ' No closer location recorded
                    closestIndex = index
                ElseIf Abs(switches.At(index).PointDistance - centerPt) < Abs(switches.At(closestIndex).PointDistance - centerPt) Then
                    ' Closer to required hand hole location
                    closestIndex = index
                End If
            End If
            If switches.At(index).PointDistance < centerPt - maximumAccessSnap Then
                ' Past maximum snap
                Exit Do
            End If
        End If
        index = index - 1
    Loop
    If closestIndex <> -1 Then
        ' Found a bore pit to swap
        switches.SetIntersectionType closestIndex, "HANDHOLE"
        centerPt = switches.At(closestIndex).PointDistance
        'Debug.Print "Found bore pit at " & centerPt
    Else
        ' Add new hand hole
        ' Try to find a safe point nearby
        Dim checkBefore As Double
        checkBefore = GetClosePole(centerPt, -1, intersections)
        
        Dim checkAfter As Double
        checkAfter = GetClosePole(centerPt, 1, intersections)

        If checkAfter - centerPt > 0.0001 And centerPt - checkBefore < 0.0001 And Not keepLeft Then
            ' Only found pole after
            centerPt = checkAfter
            'Debug.Print "Found pole after"
        ElseIf checkAfter - centerPt < 0.0001 And centerPt - checkBefore > 0.0001 Then
            ' Only found pole before
            centerPt = checkBefore
            'Debug.Print "Found pole before"
        Else
            checkAfter = getSafeLocation(centerPt, 1, intersections)
            checkBefore = getSafeLocation(centerPt, -1, intersections)
            'Debug.Print checkBefore & " before after " & checkAfter
            ' Use closest safe point
            If centerPt - checkBefore < checkAfter - centerPt Or keepLeft Then
                centerPt = checkBefore
            Else
                centerPt = checkAfter
            End If
        End If
        'Debug.Print "New Center: " & centerPt & " distance from before: " & (centerPt - distanceBefore)
        
        closestIndex = switches.LinearSearch(centerPt, 0.1, "BOREPIT")
        If closestIndex <> -1 Then
            ' A bore pit already at the location (this can occur if pole snap is larger than access snap)
            switches.SetIntersectionType closestIndex, "HANDHOLE"
        Else
            newHandholes.Add checkBefore
        End If
        
    End If
    
    ' Recursion!
    Dim nextHandholes As Collection
    Set nextHandholes = GetAccessHandholes(indexAfter, centerPt, distanceAfter, switches, intersections)
    For i = 1 To nextHandholes.count
        newHandholes.Add nextHandholes.item(i)
    Next i
    Set nextHandholes = GetAccessHandholes(GetSegmentIndex(centerPt, switches), distanceBefore, centerPt, switches, intersections)
    For i = 1 To nextHandholes.count
        newHandholes.Add nextHandholes.item(i)
    Next i
    Set GetAccessHandholes = newHandholes
End Function


' Get the distance for the point at which the segment starts in the switch list
'
' @param index      Index of the segment in the switch list
' @param switches   The switch list
Function getSegmentStartingPoint(index As Long, switches As IntersectionList) As Double
    'Look for previous bore pits
    Dim intersectionPt As IntersectionPoint
    Dim prevSegmentLength As Double
    prevSegmentLength = 0
    Dim i As Long
    i = index - 1
    Do While i >= 0
        Set intersectionPt = switches.At(i)
        If intersectionPt.isPit() Then
            ' Found pit
            getSegmentStartingPoint = intersectionPt.PointDistance + prevSegmentLength
            Exit Function
        Else
            ' Another segment before this one
            prevSegmentLength = prevSegmentLength + intersectionPt.PointDistance
        End If
        i = i - 1
    Loop
    ' Reached the start of the line
    getSegmentStartingPoint = prevSegmentLength
End Function

' Get the index of the bore or plow segment in the switch list that passes through the specified distance.
'
' @param distance   The distance to find a segment at. Any distance longer than the bore line will return the last index.
' @param switches   The switch list of bore pits and segments
Function GetSegmentIndex(distance As Double, switches As IntersectionList) As Long
    Dim intersectionPt As IntersectionPoint
    Dim totalSegmentLength As Double
    totalSegmentLength = 0
    Dim i As Long
    For i = 0 To switches.size - 1
        Set intersectionPt = switches.At(i)
        If Not intersectionPt.isPit() Then
            ' Add segment length to total
            totalSegmentLength = totalSegmentLength + intersectionPt.PointDistance
            If totalSegmentLength > distance Then
                ' last segment overtakes the distance
                GetSegmentIndex = i
                Exit Function
            End If
        End If
    Next i
    ' distance is larger than the bore length
    GetSegmentIndex = switches.size - 1
    
End Function

' Check which distance has a pole closest to it, or is at the end of the bore line.
' Undefined behavior if neither point has a pole close enough to it
'
' @param distance1      The first distance along the bore line
' @param distance2      The second distance along the bore line
' @param intersections  The list of intersections
' @returns              True if distance1 has a pole closer to it or is at the end of the bore line.
Function ChooseHandHoleRoadCrossing(distance1 As Double, distance2 As Double, intersections As IntersectionList) As Boolean
    Dim lineLength As Double
    lineLength = intersections.At(intersections.size - 1).PointDistance
    Dim distance1AtEnd As Boolean
    Dim distance2AtEnd As Boolean
    distance1AtEnd = distance1 < 0.00001 Or distance1 > lineLength + 0.00001
    distance2AtEnd = distance2 < 0.00001 Or distance2 > lineLength + 0.00001
    If distance1AtEnd And Not distance2AtEnd Then
        ChooseHandHoleRoadCrossing = True
        Exit Function
    ElseIf Not distance1AtEnd And distance2AtEnd Then
        ChooseHandHoleRoadCrossing = False
        Exit Function
    End If
    Dim closestIntersectionPt As IntersectionPoint
    Dim prevClosestIntersectionPt As IntersectionPoint
    Set closestIntersectionPt = intersections.GetIntersection(distance2, 0, "POLE")
    Set prevClosestIntersectionPt = intersections.GetIntersection(distance1, 0, "POLE")
    If closestIntersectionPt Is Nothing Then
        ChooseHandHoleRoadCrossing = False
    ElseIf prevClosestIntersectionPt Is Nothing Then
        ChooseHandHoleRoadCrossing = True
    Else
        ChooseHandHoleRoadCrossing = Abs(prevClosestIntersectionPt.PointDistance - distance1) < Abs(closestIntersectionPt.PointDistance - distance2)
    End If
    
End Function

' Check if 2 intersections should be separated from eachother, aka, have seperate bore lines, and a plow inbetween.
' The layout of how this would look like on the bore line would be:
' --------intersectionBefore------beforeExtension----------------------------afterExtension------intersectionAfter----------
' where the location of the text represents the object's distance along the bore line
'
' @param intersectionBefore     The intersection point with a smaller distance
' @param beforeExtension        The distance at which intersectionBefore would normally have a bore pit placed (further on the bore line)
' @param intersectionAfter      The intersection point with a larger distance
' @param afterExtension         The distance at which intersectionAfter would normally have a bore pit placed (closer on the bore line)
Function ShouldSeparateIntersections(intersectionBefore As IntersectionPoint, beforeExtension As Double, intersectionAfter As IntersectionPoint, afterExtension As Double) As Boolean
    Dim maxBoreConnection As Double
    maxBoreConnection = CDbl(AutoBoreForm.MaxBoreConnectionDistance)
    '                                                                               Check distance before extension (factoring the bore radii)                                                                                                                                              Check extension distances
    ShouldSeparateIntersections = (AutoBoreForm.ConnectBeforeExtension And intersectionAfter.PointDistance - intersectionAfter.GetBoreRadius() - (intersectionBefore.PointDistance + intersectionBefore.GetBoreRadius()) > maxBoreConnection) Or (Not AutoBoreForm.ConnectBeforeExtension And afterExtension - beforeExtension > maxBoreConnection)
End Function

' Creates a new intersection point
'
' @param distance   The Point's distance along the bore line
' @param pType      The type of point. See the IntersectionPoint class module for types used
' @param entry      Whether the point is an entry or exit point
Function CreateIntersectionPoint(distance As Double, pType As String, Optional entry As Boolean = True) As IntersectionPoint
    Dim intersectionPt As New IntersectionPoint
    intersectionPt.PointDistance = distance
    intersectionPt.PointType = pType
    intersectionPt.EnterPoint = entry
    Set CreateIntersectionPoint = intersectionPt
End Function


' Converts all the different intersection types to one list of objects
Function CreateIntersectionList(culvertIntersections As Collection, soilIntersections As Collection, poleIntersections As Collection, matchIntersections As Collection, roadIntersections As Collection, bridgeIntersections As Collection, drivewayIntersections As Collection, guardrailIntersections As Collection, lineLength As Double) As IntersectionList
    Dim intersections As New IntersectionList
    Dim intersection As New IntersectionPoint
    ' need to create new points maybe?????
    For i = 1 To culvertIntersections.count
        intersections.Add CreateIntersectionPoint(culvertIntersections.item(i), "CULVERT")
    Next i
    For i = 1 To soilIntersections.count
        intersections.Add CreateIntersectionPoint(soilIntersections.item(i), "SOIL", i Mod 2 = 1)
    Next i
    For i = 1 To poleIntersections.count
        intersections.Add CreateIntersectionPoint(poleIntersections.item(i), "POLE")
    Next i
    For i = 1 To guardrailIntersections.count
        intersections.Add CreateIntersectionPoint(guardrailIntersections.item(i), "GUARDRAIL")
    Next i
    For i = 1 To matchIntersections.count
        intersections.Add CreateIntersectionPoint(matchIntersections.item(i), "MATCHLINE")
    Next i
    For i = 1 To roadIntersections.count
        intersections.Add CreateIntersectionPoint(roadIntersections.item(i), "ROAD", i Mod 2 = 1)
    Next i
    For i = 1 To bridgeIntersections.count
        intersections.Add CreateIntersectionPoint(bridgeIntersections.item(i), "BRIDGE", i Mod 2 = 1)
    Next i
    For i = 1 To drivewayIntersections.count
        intersections.Add CreateIntersectionPoint(drivewayIntersections.item(i), "DRIVEWAY", i Mod 2 = 1)
    Next i
    intersections.SortList
    intersections.Add CreateIntersectionPoint(lineLength, "END")
    
    Set CreateIntersectionList = intersections
End Function

' Get the next intersection that needs to be bored under.
'
' @param startingDistance   The distance to start looking for intersections that will cause a bore (culvert, bridge, etc)
' @param direction          The direction to look for intersections to bore under
' @param intersections      The intersections on the bore line
Function GetBoreIntersection(startingDistance As Double, direction As Integer, intersections As IntersectionList) As IntersectionPoint
    Dim nextIntersection As IntersectionPoint
    Set nextIntersection = intersections.GetIntersection(startingDistance, direction)
    If Not nextIntersection Is Nothing Then
        Do While nextIntersection.GetBoreRadius() = 0 And nextIntersection.PointType <> "ROAD"
            Set nextIntersection = intersections.GetIntersection(nextIntersection.PointDistance + direction * 0.1, direction)
            If nextIntersection Is Nothing Then
                Exit Do
            End If
        Loop
    End If
    Set GetBoreIntersection = nextIntersection
End Function

' Get the distance along the bore line that the next bore pit would go for an intersection.
' Only looks at elements that would allow bore placement to be easier and not necessarily restrict it. (soil, poles, roads)
' Does not consider other bore intersections (culverts, bridges, driveways, etc).
'
' @param intersection       The intersection to find a bore pit for
' @param direction          The direction about the intersection to place the bore pit
' @param intersections      The intersections on the bore line

Function GetPitLocation(intersection As IntersectionPoint, direction As Integer, intersections As IntersectionList) As Double
    If intersection Is Nothing Then
        ' No reason to bore
        GetPitLocation = direction
    Else
        If intersection.PointType = "ROAD" Then
            ' Do not move bore pits going across roads
            GetPitLocation = intersection.PointDistance
        Else
            GetPitLocation = ExtendPit(intersection.PointDistance + (intersection.GetBoreRadius() * direction), direction, intersections)
        End If
    End If
End Function

' Extend a bore pit's location to a better position. For example: Next to a pole or out of a soil patch
'
' @param pitDistance    The distance at which the pit is located along the bore line
' @param direction      The direction along the bore line to extend
' @param intersections  The list of intersections on the bore pit
' @returns              The new distance for the bore pit
Function ExtendPit(pitDistance As Double, direction As Integer, intersections As IntersectionList) As Double
    ' Checks higher up in code have higher priority
    Dim MaxSoilExtend As Double
    MaxSoilExtend = CDbl(AutoBoreForm.MaxSoilExtend)
    Dim maxConnection As Double
    maxConnection = CDbl(AutoBoreForm.MaxBoreConnectionDistance)
    Dim MinBoreFitSize As Double
    MinBoreFitSize = CDbl(AutoBoreForm.MinBoreFitSize)
    Dim nextIntersection As IntersectionPoint
    Dim distance As Double
    
    ' Check to extend to road crossing
    ' This may not even need to be checked, because the prev intersection would have ben extended to connect to the road
    Set nextIntersection = intersections.GetIntersection(pitDistance, direction, "ROAD")
    If Not nextIntersection Is Nothing Then
        If Abs(nextIntersection.PointDistance - pitDistance) < maxConnection Then
            ExtendPit = nextIntersection.PointDistance
            Exit Function
        End If
    End If
    
    ' Check for close poles
    distance = GetClosePole(pitDistance, direction, intersections)
    If distance <> pitDistance Then
        ExtendPit = distance
        Exit Function
    End If
    
    ' Check for soil extension
    Set nextIntersection = intersections.GetIntersection(pitDistance, direction, "SOIL")
    Dim intersection1 As IntersectionPoint
    Dim intersection2 As IntersectionPoint
    If Not nextIntersection Is Nothing Then
        'Find furthest soil patches inside range
        Do While Abs(nextIntersection.PointDistance - pitDistance) < MaxSoilExtend
            If Not intersection1 Is Nothing Then Set intersection2 = intersection1
            Set intersection1 = nextIntersection
            Set nextIntersection = intersections.GetIntersection(nextIntersection.PointDistance + direction, direction, "SOIL")
            If nextIntersection Is Nothing Then Exit Do
        Loop
        If Not intersection1 Is Nothing Then
            ' Check if furthest location is safe (checking directly after and where it would be placed JIC the soil patch is small)
            If IsPitLocationSafe(intersection1.PointDistance + (MinBoreFitSize / 2 * direction) + direction * 0.1, intersections) Then
                ExtendPit = intersection1.PointDistance + (MinBoreFitSize / 2 * direction)
                Exit Function
            ElseIf Not intersection2 Is Nothing Then
                ' intersection1 is not safe after
                If IsPitLocationSafe(intersection2.PointDistance + (MinBoreFitSize / 2 * direction) + direction * 0.1, intersections) Then
                    ExtendPit = intersection2.PointDistance + (MinBoreFitSize / 2 * direction)
                    Exit Function
                End If
            End If
        End If
    End If
    
    'Get next safe location by iterating through the whole line
    
    ExtendPit = getSafeLocation(pitDistance, direction, intersections)
End Function

Function getSafeLocation(pitDistance As Double, direction As Integer, intersections As IntersectionList) As Double
    Dim MinBoreFitRadius As Double
    MinBoreFitRadius = CDbl(AutoBoreForm.MinBoreFitSize) / 2
    Dim newDistance As Double
    newDistance = pitDistance
    Do While Not IsPitLocationSafe(newDistance, intersections)
        newDistance = newDistance + (MinBoreFitRadius * direction)
        If newDistance < 0 Then
            newDistance = 0
            Exit Do
        ElseIf newDistance > intersections.At(intersections.size() - 1).PointDistance Then
            newDistance = intersections.At(intersections.size() - 1).PointDistance
            Exit Do
        End If
    Loop
    getSafeLocation = newDistance
End Function

' Gets a safe pole close to a bore pit. Only checks for poles close enough to the maxPoleExtend setting.
'
' @param pitDistance    The distance along the line that the bore pit is.
' @param direction      The direction along the bore line to search for a pole
' @param intersections  The intersections along the bore line.
Function GetClosePole(pitDistance As Double, direction As Integer, intersections As IntersectionList) As Double
    Dim maxPoleExtend As Double
    maxPoleExtend = CDbl(AutoBoreForm.maxPoleSnap)
    Dim nextIntersection As IntersectionPoint
    Set nextIntersection = intersections.GetIntersection(pitDistance, direction, "POLE")
    Dim MinBoreFitRadius As Double
    MinBoreFitRadius = CDbl(AutoBoreForm.MinBoreFitSize) / 2
    If Not nextIntersection Is Nothing Then
        Do While Abs(nextIntersection.PointDistance - pitDistance) < maxPoleExtend
            If IsPitLocationSafe(nextIntersection.PointDistance, intersections) Then
                ' Found a safe pole location
                GetClosePole = nextIntersection.PointDistance
                Exit Function
            ElseIf IsPitLocationSafe(nextIntersection.PointDistance + MinBoreFitRadius, intersections) Then
                GetClosePole = nextIntersection.PointDistance + MinBoreFitRadius
                Exit Function
            End If
            Set nextIntersection = intersections.GetIntersection(nextIntersection.PointDistance + direction, direction, "POLE")
            If nextIntersection Is Nothing Then Exit Do
        Loop
    End If
    GetClosePole = pitDistance
End Function

Function IsPitLocationSafe(distance As Double, intersections As IntersectionList) As Boolean
    Dim MinBoreFitRadius As Double
    MinBoreFitRadius = CDbl(AutoBoreForm.MinBoreFitSize) / 2
    Dim lineSize As Double
    lineSize = intersections.At(intersections.size - 1).PointDistance
    If distance < 0 Or distance > lineSize Then
        ' Out of bounds
        IsPitLocationSafe = False
        Exit Function
    End If
    For i = -1 * MinBoreFitRadius To MinBoreFitRadius Step 10
        If distance + i < lineSize And distance + i > 0 And Not isLocationSafe(distance + i, intersections) Then
            IsPitLocationSafe = False
            Exit Function
        End If
    Next i
    IsPitLocationSafe = True
End Function

' Check if a location is safe at a distance along the bore line
'
' @param distance       Distance along the bore line to check.
' @param intersections  Intersections along the bore line that could cause it to be unsafe.
' @returns              True if the point is safe
Function isLocationSafe(distance As Double, intersections As IntersectionList) As Boolean
    If intersections.IsBetweenIntersections(distance, "SOIL") Or intersections.IsBetweenIntersections(distance, "ROAD") Or intersections.IsBetweenIntersections(distance, "BRIDGE") Then
        ' Between soil, bridge, or road
        isLocationSafe = False
        Exit Function
    End If
    
    ' Check if inside a bore radius
    Dim intersectionPt As IntersectionPoint
    Set intersectionPt = GetBoreIntersection(distance, 1, intersections)
    If Not intersectionPt Is Nothing Then
        If intersectionPt.PointDistance - intersectionPt.GetBoreRadius() < distance Then
            ' Inside a bore radius
            isLocationSafe = False
            Exit Function
        End If
    End If
    Set intersectionPt = GetBoreIntersection(distance, -1, intersections)
    If Not intersectionPt Is Nothing Then
        If intersectionPt.PointDistance + intersectionPt.GetBoreRadius() > distance Then
            ' Inside a bore radius
            isLocationSafe = False
            Exit Function
        End If
    End If
    
    ' Check if between a guardrail and bridge
    Dim maxGuardrailBridge As Double
    maxGuardrailBridge = CDbl(AutoBoreForm.MaxGuardrailBridgeDistance)
    ' Get the distance between guardrail and bridge around this point
    Dim foundDistance As Double
    foundDistance = intersections.GetIntersectionDistance(distance, "BRIDGE", "GUARDRAIL")
    If foundDistance <> -1 And foundDistance < maxGuardrailBridge Then
        isLocationSafe = False
        Exit Function
    End If
    
    'Check if too close to matchline
    Set intersectionPt = intersections.GetIntersection(distance, 1, "MATCHLINE")
    If Not intersectionPt Is Nothing Then
        If intersectionPt.PointDistance - distance < 6 Then
            ' too close
            isLocationSafe = False
            Exit Function
        End If
    End If
    Set intersectionPt = intersections.GetIntersection(distance, -1, "MATCHLINE")
    If Not intersectionPt Is Nothing Then
        If distance - intersectionPt.PointDistance < 6 Then
            ' too close
            isLocationSafe = False
            Exit Function
        End If
    End If
    
    isLocationSafe = True
End Function

Attribute VB_Name = "UpdateModule"
Public updateString As String
Public downloadLink As String

Public Function CheckUpdate()
    updateString = ""
    downloadLink = ""
    Const curVersion As String = "2.5"
    Dim jsonResponse As String
    jsonResponse = GetLatestRelease()
    If jsonResponse <> "" Then
        Dim tag As String
        tag = ParseJsonString(jsonResponse, "tag_name")
        
        If tag <> "" Then
            If InStr(tag, "v") = 1 Then tag = Right(tag, Len(tag) - 1) ' remove the v
            If CDbl(tag) > CDbl(curVersion) Then
                updateString = "Update available! v" & curVersion & " -> v" & tag & vbNewLine & "Click to download."
            End If
        End If
        
        Dim updateLink As String
        updateLink = ParseJsonString(jsonResponse, "zipball_url")
        If updateLink <> "" Then
            downloadLink = updateLink
        Else
            downloadLink = "https://github.com/No-Not-Jaden/AutoBore/releases"
        End If
    End If
    
End Function

'-- Fetch latest release tag ------------------------------------------
Private Function GetLatestRelease() As String
    Const GITHUB_REPO  As String = "No-Not-Jaden/AutoBore"
    Const GITHUB_TOKEN As String = ""
    Dim httpReq       As Object
    Dim apiUrl        As String
    Dim respText      As String
    
    apiUrl = "https://api.github.com/repos/" & GITHUB_REPO & "/releases/latest"
    
    Set httpReq = CreateObject("WinHttp.WinHttpRequest.5.1")
    
    With httpReq
        .Open "GET", apiUrl, False
        .setRequestHeader "Accept", "application/vnd.github+json"
        ' GitHub requires a User-Agent header
        .setRequestHeader "X-GitHub-Api-Version", "2022-11-28"
        ' Only set Authorization if token is available
        If GITHUB_TOKEN <> "" Then
            .setRequestHeader "Authorization", "Bearer " & GITHUB_TOKEN
        End If
        On Error GoTo cantconnect
        .send
    End With
    
    If httpReq.Status = 200 Then
        respText = httpReq.ResponseText
        GetLatestRelease = respText
    Else
        Debug.Print "GitHub API error: " & httpReq.Status & " – " & httpReq.StatusText
        'Debug.Print "Response headers: " & vbCrLf & httpReq.GetAllResponseHeaders()
        Debug.Print "Response body: " & vbCrLf & httpReq.ResponseText
cantconnect:
        GetLatestRelease = ""
    End If
End Function

'-- Simple JSON value extractor (for top-level string values) ---------
Private Function ParseJsonString(json As String, key As String) As String
    Dim searchKey As String
    Dim p1        As Long, p2 As Long
    
    searchKey = """" & key & """" & ":"  ' e.g. "tag_name":
    p1 = InStr(json, searchKey)
    If p1 = 0 Then Exit Function
    
    ' advance past the key and any whitespace/quotes
    p1 = InStr(p1 + Len(searchKey), json, """")
    If p1 = 0 Then Exit Function
    
    p2 = InStr(p1 + 1, json, """")
    If p2 = 0 Then Exit Function
    
    ParseJsonString = mid$(json, p1 + 1, p2 - p1 - 1)
End Function

Attribute VB_Name = "Utils"


Function ConvertElement()
    Dim ee As ElementEnumerator
    Dim oScanCriteria As ElementScanCriteria
    Set oScanCriteria = New ElementScanCriteria
    oScanCriteria.ExcludeAllLevels
    oScanCriteria.IncludeLevel ActiveModelReference.Levels("Exist Right of Way Line")
    oScanCriteria.ExcludeAllLineStyles
    oScanCriteria.IncludeLineStyle ActiveDesignFile.LineStyles("7")
    Set ee = ActiveModelReference.Scan(oScanCriteria)
    While ee.MoveNext
        ee.Current.Level = ActiveModelReference.Levels("Exist Horizontal Alignment")
        ee.Current.Rewrite
        ee.Current.Redraw
    Wend
End Function

'Returns a collection of Element objects within the radius
Function NearbyElements(origin As Point3d, radius As Double) As Collection
    Dim oElem As Element
    Set oElem = CreateEllipseElement2(Nothing, origin, radius, radius, Matrix3dIdentity)
    
    Set NearbyElements = ElementsInside(oElem)
    
End Function

'Returns a collection of Element objects within the radius
Function ElementsInside(oElem As ClosedElement) As Collection
    
    Dim oFence As Fence
    Dim myView As View
    
     With ActiveSettings
        .FenceClip = False
        .FenceOverlap = True
        .FenceVoid = False
    End With

    Set oFence = ActiveDesignFile.Fence
    oFence.Undefine

    Set myView = CommandState.LastView

    oFence.DefineFromElement myView, oElem
    'Is this needed?
    oFence.Draw
    'Debug.Print "View: " & oFence.
    'See CopyFenceContents() example to possible implement saving the active settings (probably should do outside this method)
    Dim ee As ElementEnumerator
    Set ee = oFence.GetContents(False)
    
    Dim includedElements As New Collection
    
    While ee.MoveNext
        Dim ele As Element
        ' vv This is now false vv
        '  ee.Current is returning a copy of the element
        '  because this program called GetContents with
        '  the CloneElements argument set to True.
        Set ele = ee.Current
        includedElements.Add ele
    Wend
    Set ElementsInside = includedElements
    
End Function

Public Function startsWith(str As String, prefix As String) As Boolean
    startsWith = Left(str, Len(prefix)) = prefix
End Function

Public Function Max(x, y As Variant) As Variant
  Max = IIf(x > y, x, y)
End Function

Public Function Min(x, y As Variant) As Variant
   Min = IIf(x < y, x, y)
End Function

Public Function CreateActionPoint(pType As String, pDistance As Double) As ActionPoint
    Dim interestPoint As New ActionPoint
    interestPoint.PointType = pType
    interestPoint.PointDistance = pDistance
    Set CreateActionPoint = interestPoint
End Function

Public Function CreateReferencedActionPoint(distance As Double, referenced As Long) As ReferencedActionPoint
    Dim interestPoint As New ReferencedActionPoint
    interestPoint.PointDistance = distance
    interestPoint.PointReference = referenced
    Set CreateReferencedActionPoint = interestPoint
End Function

Public Function CreateBorePit(rightOfWay As Point3d, point As Point3d, edge As Point3d) As Element
    Dim reference As ComplexShapeElement
    'Scan file for bore template
    Dim oScanCriteria As ElementScanCriteria
    Set oScanCriteria = New ElementScanCriteria
    oScanCriteria.ExcludeAllLevels
    oScanCriteria.IncludeLevel ActiveDesignFile.Levels("Level 12")
    oScanCriteria.ExcludeAllTypes
    oScanCriteria.IncludeType msdElementTypeComplexShape
    Dim oScanEnumerator As ElementEnumerator
    Set oScanEnumerator = ActiveModelReference.Scan(oScanCriteria)
    If oScanEnumerator.MoveNext Then
        Set reference = oScanEnumerator.Current.AsComplexShapeElement
    Else
        'No Bore Pit template
        Debug.Print "No bore pit template found"
        Set CreateBorePit = Nothing
        Exit Function
    End If
    Dim cc As New CopyContext
    cc.AddElementToModel = False
    Dim bore As ComplexShapeElement
    Set bore = ActiveModelReference.CopyElement(reference, cc).AsComplexShapeElement
    Dim ee As ElementEnumerator
    Set ee = bore.GetSubElements
    Dim ele As ChainableElement
    If ee.MoveNext Then
        Set ele = ee.Current.AsChainableElement
    End If
    Dim parallel As Vector3d
    parallel = Vector3dSubtractPoint3dPoint3d(edge, point)
    Dim moveDistance As Point3d
    moveDistance = Point3dSubtract(rightOfWay, ele.startPoint)
    bore.Move moveDistance
    
    Dim boreVector As Vector3d
    boreVector = Vector3dSubtractPoint3dPoint3d(ele.startPoint, ele.endPoint)
    Dim theta As Double
    theta = Vector3dAngleBetweenVectorsXY(parallel, boreVector)
    RotateElementAboutZ bore, rightOfWay, (theta * -1)
    
    moveDistance = Point3dFromVector3d(parallel)
    bore.Move moveDistance
    
    'Check if outside the R/W
    If Point3dDistance(bore.Centroid, point) > 5 And ee.MoveNext Then
        'Outside
        Set ele = ee.Current
        moveDistance = Point3dScale(Point3dNormalize(Point3dSubtract(point, rightOfWay)), ele.length)
        bore.Move moveDistance
    End If
    
    Set CreateBorePit = bore
End Function

Public Function CreateHandHole(rightOfWay As Point3d, point As Point3d, edge As Point3d) As Element
    Dim reference As CellElement
    'Scan file for bore template
    Dim oScanCriteria As ElementScanCriteria
    Set oScanCriteria = New ElementScanCriteria
    oScanCriteria.ExcludeAllTypes
    oScanCriteria.IncludeType msdElementTypeCellHeader
    Dim oScanEnumerator As ElementEnumerator
    Set oScanEnumerator = ActiveModelReference.Scan(oScanCriteria)
    Do While oScanEnumerator.MoveNext
        If oScanEnumerator.Current.AsCellElement.name = "EXIST UTILITIES TELEPHONE HAND HOLE" Then
            Set reference = oScanEnumerator.Current
            Exit Do
        End If
    Loop
    If reference Is Nothing Then
        'No Hand Hole template
        Debug.Print "No hand hole template found"
        Set CreateHandHole = Nothing
        Exit Function
    End If
        
    Dim cc As New CopyContext
    cc.AddElementToModel = False
    Dim bore As CellElement
    Set bore = ActiveModelReference.CopyElement(reference, cc).AsCellElement
    
    Dim parallel As Vector3d
    parallel = Vector3dSubtractPoint3dPoint3d(edge, point)
    Dim moveDistance As Point3d
    moveDistance = Point3dSubtract(rightOfWay, bore.origin)
    bore.Move moveDistance
    
    Dim ee As ElementEnumerator
    Set ee = bore.GetSubElements
    Dim ee2 As ElementEnumerator
    Dim boreVector As Vector3d
    Do While ee.MoveNext
        If ee.Current.IsComplexStringElement Then
            Set ee2 = ee.Current.AsComplexStringElement.GetSubElements
            If ee2.MoveNext Then
                boreVector = Vector3dSubtractPoint3dPoint3d(ee2.Current.AsLineElement.startPoint, ee2.Current.AsLineElement.endPoint)
                Exit Do
            End If
        End If
    Loop
    
    Dim theta As Double
    theta = Vector3dAngleBetweenVectorsXY(parallel, boreVector)
    RotateElementAboutZ bore, rightOfWay, (theta * -1)
    
    'Move closer inside R/W
    moveDistance = Point3dScale(Point3dNormalize(Point3dSubtract(point, rightOfWay)), (5.725 / 2))
    bore.Move moveDistance
    
    Set CreateHandHole = bore
End Function

Function getRotationMatrix(v1 As Vector3d, v2 As Vector3d) As Matrix3d
    Dim theta As Double
    theta = Vector3dAngleBetweenVectorsXY(v1, v2)
    Dim Axis As Point3d
    Axis.x = 0
    Axis.y = 0
    Axis.Z = 1
    getRotationMatrix = Matrix3dFromVectorAndRotationAngle(Axis, theta * -1)
End Function

Function RotateElementAboutZ(ele As Element, pntFixed As Point3d, dblRadians As Double)
    Dim RotationMatrix As Matrix3d
    Dim Eltrans As Transform3d

    '  Create a rotation matrix for rotating with the Z direction fixed.
    Dim Axis As Point3d
    Axis.x = 0
    Axis.y = 0
    Axis.Z = 1
    RotationMatrix = Matrix3dFromVectorAndRotationAngle(Axis, dblRadians)

    Eltrans = Transform3dFromMatrix3dAndFixedPoint3d(RotationMatrix, pntFixed)

    '  Apply the transform to rotate the element
    ele.Transform Eltrans
End Function

Public Function CreateBoreText(origin As Point3d, distance As String) As TextNodeElement
    Dim textContent As String
    Dim reference As TextNodeElement
    'Scan file for bore template
    Dim oScanCriteria As ElementScanCriteria
    Set oScanCriteria = New ElementScanCriteria
    oScanCriteria.ExcludeAllLevels
    oScanCriteria.IncludeLevel ActiveDesignFile.Levels("Level 30")
    oScanCriteria.ExcludeAllTypes
    oScanCriteria.IncludeType msdElementTypeTextNode
    Dim oScanEnumerator As ElementEnumerator
    Set oScanEnumerator = ActiveModelReference.Scan(oScanCriteria)
    If oScanEnumerator.MoveNext Then
        Set reference = oScanEnumerator.Current.AsTextNodeElement
    Else
        'No Bore Pit template
        Debug.Print "No bore pit text template found"
    End If
    Set reference = CreateTextNodeElement1(reference, origin, Matrix3dIdentity)
    reference.AddTextLine "BORE PIT: "
    reference.AddTextLine distance & "' TO EOP"
    reference.AddTextLine "0' TO R/W"
    reference.AddTextLine "3'WIDE"
    reference.AddTextLine "4'LONG"
    reference.AddTextLine "4'DEEP"
    Set oScanEnumerator = reference.GetSubElements
    oScanEnumerator.MoveNext
    Dim scaleAmount As Double
    scaleAmount = 3.1298 / oScanEnumerator.Current.AsTextElement.TextStyle.height
    reference.ScaleUniform reference.origin, scaleAmount
    Set CreateBoreText = reference
End Function

Public Function CreateHandHoleText(origin As Point3d, distance As String) As TextNodeElement
    Dim textContent As String
    Dim reference As TextNodeElement
    'Scan file for bore template
    Dim oScanCriteria As ElementScanCriteria
    Set oScanCriteria = New ElementScanCriteria
    oScanCriteria.ExcludeAllLevels
    oScanCriteria.IncludeLevel ActiveDesignFile.Levels("Level 30")
    oScanCriteria.ExcludeAllTypes
    oScanCriteria.IncludeType msdElementTypeTextNode
    Dim oScanEnumerator As ElementEnumerator
    Set oScanEnumerator = ActiveModelReference.Scan(oScanCriteria)
    If oScanEnumerator.MoveNext Then
        Set reference = oScanEnumerator.Current.AsTextNodeElement
    Else
        'No Bore Pit template
        Debug.Print "No hand hole text template found"
    End If
    Set reference = CreateTextNodeElement1(reference, origin, Matrix3dIdentity)
    reference.AddTextLine "BORE PIT:"
    reference.AddTextLine distance & "' TO EOP 0' TO R/W"
    reference.AddTextLine "3'WIDEx4'LONGx4'DEEP"
    reference.AddTextLine "TO BE REPLACED WITH"
    reference.AddTextLine "ANSI/SCTE Tier 22"
    reference.AddTextLine "HANDHOLE"
    Set oScanEnumerator = reference.GetSubElements
    oScanEnumerator.MoveNext
    Dim scaleAmount As Double
    scaleAmount = 3.1298 / oScanEnumerator.Current.AsTextElement.TextStyle.height
    reference.ScaleUniform reference.origin, scaleAmount
    Set CreateHandHoleText = reference
End Function

'lineType:
'0 - plow along
'1 - bore along
'2 - bore across
Public Function CreateBoreDimension(origin As Point3d, distance As String, roadName As String, lineType As Integer) As TextNodeElement
    Dim textContent As String
    Dim reference As TextNodeElement
    If lineType = 0 Then
        'Plow Along
        Set reference = GetPlowAlongTemplate()
        textContent = "PLOW" & vbNewLine & distance & " FEET ALONG " & roadName & vbNewLine & "1-2"" CONDUIT AT A" & vbNewLine & "DEPTH OF 3 FEET BELOW GROUND"
    ElseIf lineType = 1 Then
        'Bore Along
        Set reference = GetBoreAlongTemplate()
        textContent = "DIRECTIONAL BORE" & vbNewLine & distance & " FEET ALONG " & roadName & vbNewLine & "1-2"" CONDUIT AT A" & vbNewLine & "DEPTH OF 3 FEET BELOW GROUND" & vbNewLine & "& 5 FEET BELOW PIPES"
    ElseIf lineType = 2 Then
        'Bore Across
        Set reference = GetBoreAcrossTemplate()
        textContent = "DIRECTIONAL BORE" & vbNewLine & distance & " FEET ACROSS " & roadName & vbNewLine & "1-2"" CONDUIT AT A" & vbNewLine & "DEPTH OF 10 FEET"
    End If
    Dim cc As New CopyContext
    cc.AddElementToModel = False
    Dim oElement As TextNodeElement
    Set oElement = ActiveModelReference.CopyElement(reference, cc)
    Dim moveDistance As Point3d
    moveDistance = Point3dSubtract(origin, reference.origin)
    oElement.Move moveDistance
    Dim refColor As Long
    refColor = reference.Color
    
    If lineType = 0 Then
        oElement.TextLine(2) = distance & " FEET ALONG " & roadName
    ElseIf lineType = 1 Then
        oElement.TextLine(2) = distance & " FEET ALONG " & roadName
    ElseIf lineType = 2 Then
        oElement.TextLine(2) = distance & " FEET ACROSS " & roadName
    End If
    oElement.Color = refColor
    Set CreateBoreDimension = oElement
End Function

Private Function GetPlowAlongTemplate() As TextNodeElement
    Dim reference As TextNodeElement
    'Scan file for template
    Dim oScanCriteria As ElementScanCriteria
    Set oScanCriteria = New ElementScanCriteria
    oScanCriteria.ExcludeAllLevels
    oScanCriteria.IncludeLevel ActiveDesignFile.Levels("CATV Line UBO Text")
    oScanCriteria.ExcludeAllTypes
    oScanCriteria.IncludeType msdElementTypeTextNode
    Dim oScanEnumerator As ElementEnumerator
    Set oScanEnumerator = ActiveModelReference.Scan(oScanCriteria)
    While oScanEnumerator.MoveNext
        Set reference = oScanEnumerator.Current.AsTextNodeElement
        If reference.TextLine(1) = "PLOW" Then
            Set GetPlowAlongTemplate = reference
            Exit Function
        End If
    Wend
    Debug.Print "No plow along text template found"
    Set GetPlowAlongTemplate = Nothing
End Function

Private Function GetBoreAlongTemplate() As TextNodeElement
    Dim reference As TextNodeElement
    'Scan file for template
    Dim oScanCriteria As ElementScanCriteria
    Set oScanCriteria = New ElementScanCriteria
    oScanCriteria.ExcludeAllLevels
    oScanCriteria.IncludeLevel ActiveDesignFile.Levels("CATV Line UBO Text")
    oScanCriteria.ExcludeAllTypes
    oScanCriteria.IncludeType msdElementTypeTextNode
    Dim oScanEnumerator As ElementEnumerator
    Set oScanEnumerator = ActiveModelReference.Scan(oScanCriteria)
    While oScanEnumerator.MoveNext
        Set reference = oScanEnumerator.Current.AsTextNodeElement
        If reference.TextLine(1) = "DIRECTIONAL BORE" And InStr(reference.TextLine(2), "ALONG") <> 0 Then
            Set GetBoreAlongTemplate = reference
            Exit Function
        End If
    Wend
    Debug.Print "No bore along text template found"
    Set GetBoreAlongTemplate = Nothing
End Function

Private Function GetBoreAcrossTemplate() As TextNodeElement
    Dim reference As TextNodeElement
    'Scan file for template
    Dim oScanCriteria As ElementScanCriteria
    Set oScanCriteria = New ElementScanCriteria
    oScanCriteria.ExcludeAllLevels
    oScanCriteria.IncludeLevel ActiveDesignFile.Levels("CATV Line UBO Text")
    oScanCriteria.ExcludeAllTypes
    oScanCriteria.IncludeType msdElementTypeTextNode
    Dim oScanEnumerator As ElementEnumerator
    Set oScanEnumerator = ActiveModelReference.Scan(oScanCriteria)
    While oScanEnumerator.MoveNext
        Set reference = oScanEnumerator.Current.AsTextNodeElement
        If reference.TextLine(1) = "DIRECTIONAL BORE" And InStr(reference.TextLine(2), "ACROSS") <> 0 Then
            Set GetBoreAcrossTemplate = reference
            Exit Function
        End If
    Wend
    Debug.Print "No bore across text template found"
    Set GetBoreAcrossTemplate = Nothing
End Function

Function getDimensionTemplate() As dimensionElement
    Dim reference As dimensionElement
    'Scan file for template
    Dim oScanCriteria As ElementScanCriteria
    Set oScanCriteria = New ElementScanCriteria
    oScanCriteria.ExcludeAllLevels
    oScanCriteria.IncludeLevel ActiveDesignFile.Levels("Level 30")
    oScanCriteria.ExcludeAllTypes
    oScanCriteria.IncludeType msdElementTypeDimension
    Dim oScanEnumerator As ElementEnumerator
    Set oScanEnumerator = ActiveModelReference.Scan(oScanCriteria)
    If oScanEnumerator.MoveNext Then
        Set reference = oScanEnumerator.Current
    End If
    Set getDimensionTemplate = reference
End Function

Function printList(point_list As PointList)
    Debug.Print "Current List: "
    Dim aPoint As ActionPoint
    Dim i As Long
    For i = 0 To point_list.size - 1
        Set aPoint = point_list.At(i)
        Debug.Print i & ": " & aPoint.PointDistance & " = " & aPoint.PointType
    Next i
End Function

Attribute VB_Name = "clsCandidatePoint"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Private m_pt As Point3d
Private m_clearance As Double
Private m_used As Boolean
Private m_score As Double

Public Property Get pt() As Point3d
    pt = m_pt
End Property

Public Property Let pt(value As Point3d)
    m_pt = value
End Property

Public Property Get clearance() As Double
    clearance = m_clearance
End Property

Public Property Let clearance(value As Double)
    m_clearance = value
End Property

Public Property Get used() As Boolean
    used = m_used
End Property

Public Property Let used(value As Boolean)
    m_used = value
End Property

' make points across a centerline have much much lower scores
Public Function ComputeScore(origin As Point3d, boreLine As ChainableElement, intersectingCenterline As Boolean)
    Dim originDistance As Double
    originDistance = boreLine.DistanceAtPoint(origin)
    Dim boreDirection As Vector3d
    boreDirection = Vector3dSubtractPoint3dPoint3d(boreLine.PointAtDistance(originDistance - 0.1), boreLine.PointAtDistance(originDistance + 0.1))
    Dim pointVector As Vector3d
    pointVector = Vector3dSubtractPoint3dPoint3d(origin, pt)
    Dim angleBetween As Double
    ' This should be close to perpendicular, so -pi/2 or +pi/2
    angleBetween = Abs(Vector3dAngleBetweenVectorsXY(boreDirection, pointVector))
    Dim angleGoalDistance As Double
    ' Worst angle would be 0 or pi
    angleGoalDistance = Abs(Pi / 2 - angleBetween) * 5
    'Debug.Print "clearance: " & m_clearance & " score: " & angleGoalDistance & " angle: " & angleBetween
    m_score = Utils.Min(m_clearance, Math.Sqr(boreLine.length) * 6) - (Vector3dMagnitude(pointVector) / 4) - angleGoalDistance
    If intersectingCenterline Then m_score = m_score - 90
End Function

Public Property Get score() As Double
    score = m_score
End Property

Attribute VB_Name = "modFindOpenSpaces"
Option Explicit


Private Const EPS As Double = 0.000000001 ' A small epsilon for comparisons

Function FindOpenSpaces( _
    ByVal boundingBox As ComplexShapeElement, _
    ByVal elements As Collection, _
    ByVal d As Double, origin As Point3d, boreLine As ChainableElement, centerlines As Collection) As Collection
    
    Dim result As New Collection
    
    Dim bboxVerts() As Point3d
    bboxVerts = GetRectangleVerticesFromComplexShape(boundingBox)
    
    ' Generate candidate points as clsCandidatePoint objects
    Dim points() As clsCandidatePoint
    points = GenerateCandidatePoints(bboxVerts, d)
    'DrawUnscoredSpaces points
    Debug.Print "gen: " & UBound(points)
    
    ' Compute minimum distances
    Dim i As Long
    Dim j As Long
    Dim k As Long
    For i = LBound(points) To UBound(points)
        points(i).clearance = ComputeMinimumDistance(points(i).pt, elements, bboxVerts)
        ' Check if ray from origin to point is intersecting the centerline
        Dim intersectingCenterline As Boolean
        intersectingCenterline = False
        Dim rayLine As LineElement
        Set rayLine = CreateLineElement2(Nothing, origin, points(i).pt)
        Dim iPoints() As Point3d
        ' Iterate through all centerlines in map
        For j = 1 To centerlines.count
            iPoints = rayLine.GetIntersectionPoints(centerlines.item(j), Matrix3dIdentity)
            ' Check if there is an intersection
            If UBound(iPoints) <> -1 Then
                ' Check if any of the intersections are more than 10 feet away from the origin
                ' If an intersection is too close, the centerline can be ignored
                For k = LBound(iPoints) To UBound(iPoints)
                    If Point3dDistance(origin, iPoints(k)) > 10 Then
                        intersectingCenterline = True
                        Exit For
                    End If
                Next k
                If intersectingCenterline Then Exit For
            End If
        Next j
        points(i).ComputeScore origin, boreLine, intersectingCenterline
    Next i
    
    ' Filter by distance
    Dim filteredPoints As Collection
    Set filteredPoints = FilterByDistance(points, d)
    
    
    SortByClearance filteredPoints
    
    'DrawSpaces filteredPoints
    
    Set FindOpenSpaces = getOpenSpaces(filteredPoints, d)
    
    ' Identify regions
    'Dim regions As Collection
    'Set regions = IdentifyRegions(filteredPoints, d)
    '
    '
    '' For each region, place points
    'Dim r As Long
    'Dim regionPoints As Collection
    'For r = 1 To regions.Count
    '    Set regionPoints = regions(r)
    '    SortByClearance regionPoints
    '    Dim placedPoints As Collection
    '    Set placedPoints = PlacePointsInRegion(regionPoints, d)
    '
    '    Dim p As Long
    '    For p = 1 To placedPoints.Count
    '        result.Add placedPoints(p)
    '    Next p
    'Next r
    
    'Set FindOpenSpaces = result
End Function

Private Function getOpenSpaces(sortedPoints As Collection, d As Double) As Collection
    Dim finalPoints As New Collection
    Dim point As clsCandidatePoint
    Dim finalPoint As clsCandidatePoint
    Dim tooClose As Boolean
    Dim i As Long
    Dim j As Long
    For i = 1 To sortedPoints.count
        Set point = sortedPoints.item(i)
        tooClose = False
        For j = 1 To finalPoints.count
            Set finalPoint = finalPoints.item(j)
            If Point3dDistanceXY(point.pt, finalPoint.pt) < d Then
                ' Too close to another point
                tooClose = True
                Exit For
            End If
        Next j
        If Not tooClose Then finalPoints.Add point
    Next i
    Set getOpenSpaces = finalPoints
End Function

'-----------------------------------------
' Extracting Rectangle Vertices from ComplexShapeElement
'-----------------------------------------
Private Function GetRectangleVerticesFromComplexShape(csElem As ComplexShapeElement) As Point3d()
    ' We assume the complex shape element has exactly 4 lines forming a rectangle.
    ' Steps:
    ' 1. Get sub-elements
    ' 2. Extract line elements and their endpoints
    ' 3. Deduce the rectangle's 4 unique corners
    ' 4. Order them in a polygonal sequence
    
    Dim ee As ElementEnumerator
    Set ee = csElem.GetSubElements()
    
    Dim lines As New Collection
    While ee.MoveNext
        Dim subElem As Element
        Set subElem = ee.Current
        If subElem.IsLineElement Then
            lines.Add subElem
        End If
    Wend
    
    If lines.count <> 4 Then
        Debug.Print lines.count
        Err.Raise vbObjectError, , "Expected 4 lines in the complex shape bounding box."
    End If
    
    Dim allPoints() As Point3d
    ReDim allPoints(0 To 7) ' 4 lines * 2 endpoints = 8 points, but 4 unique
    Dim idx As Long
    idx = 0
    
    Dim lElem As LineElement
    Dim i As Long
    For i = 1 To lines.count
        Set lElem = lines(i)
        Dim verts() As Point3d
        verts = lElem.GetVertices()
        allPoints(idx) = verts(0)
        idx = idx + 1
        allPoints(idx) = verts(1)
        idx = idx + 1
    Next i
    
    ' Find unique points
    Dim uniquePts() As Point3d
    uniquePts = UniquePoints(allPoints)
    If UBound(uniquePts) <> 3 Then
        Err.Raise vbObjectError, , "Could not find exactly 4 unique corners."
    End If
    
    ' Order the corners to form a polygon (rectangle).
    ' A rectangle can be ordered by choosing the point with lowest X+Y as start, then sorting the others
    ' by angle or just finding the correct order by checking distances.
    
    uniquePts = OrderRectangle(uniquePts)
    GetRectangleVerticesFromComplexShape = uniquePts
End Function

Private Function UniquePoints(pts() As Point3d) As Point3d()
    Dim temp As New Collection
    Dim i As Long, j As Long
    Dim isUnique As Boolean
    Dim p As Point3d
    
    For i = LBound(pts) To UBound(pts)
        isUnique = True
        For j = 1 To temp.count
            p = temp.item(j)
            If PointsEqual(pts(i), p) Then
                isUnique = False
                Exit For
            End If
        Next j
        If isUnique Then
            temp.Add pts(i)
        End If
    Next i
    
    Dim result() As Point3d
    ReDim result(0 To temp.count - 1)
    For i = 1 To temp.count
        result(i - 1) = temp(i)
    Next i
    
    UniquePoints = result
End Function

Private Function OrderRectangle(pts() As Point3d) As Point3d()
    ' For a rectangle, find the left-bottom corner (min X+Y)
    Dim i As Long
    Dim minSum As Double
    minSum = 1E+30
    Dim minIndex As Long
    For i = 0 To UBound(pts)
        Dim s As Double
        s = pts(i).x + pts(i).y
        If s < minSum Then
            minSum = s
            minIndex = i
        End If
    Next i
    
    Dim ordered() As Point3d
    ReDim ordered(0 To 3)
    ordered(0) = pts(minIndex)
    
    ' Get the other three
    Dim remaining(0 To 2) As Point3d ' Renamed from rem to remaining
    Dim idx As Long
    idx = 0
    Dim j As Long
    For j = 0 To UBound(pts)
        If j <> minIndex Then
            remaining(idx) = pts(j)
            idx = idx + 1
        End If
    Next j
    
    ' Sort remaining by angle relative to the first point
    Dim angles(0 To 2) As Double
    For i = 0 To 2
        angles(i) = Atan2(remaining(i).y - ordered(0).y, remaining(i).x - ordered(0).x)
    Next i
    
    ' Simple bubble sort by angle
    Dim k As Long
    For i = 0 To 1
        For k = i + 1 To 2
            If angles(k) < angles(i) Then
                Dim tempAngle As Double
                Dim tempPt As Point3d
                tempAngle = angles(i)
                angles(i) = angles(k)
                angles(k) = tempAngle
                
                tempPt = remaining(i)
                remaining(i) = remaining(k)
                remaining(k) = tempPt
            End If
        Next k
    Next i
    
    ordered(1) = remaining(0)
    ordered(2) = remaining(1)
    ordered(3) = remaining(2)
    
    OrderRectangle = ordered
End Function

Private Function PointsEqual(a As Point3d, b As Point3d) As Boolean
    PointsEqual = (Abs(a.x - b.x) < EPS And Abs(a.y - b.y) < EPS)
End Function

Private Function Atan2(yVal As Double, xVal As Double) As Double
    ' Implement atan2 if needed; VBA doesn't have a built-in atan2
    If xVal > 0 Then
        Atan2 = Atn(yVal / xVal)
    ElseIf xVal < 0 Then
        Atan2 = Atn(yVal / xVal) + Sgn(yVal) * 3.14159265358979
    Else
        If yVal > 0 Then
            Atan2 = 3.14159265358979 / 2
        ElseIf yVal < 0 Then
            Atan2 = -3.14159265358979 / 2
        Else
            ' Atan2(0,0) is undefined, return 0 for safety
            Atan2 = 0
        End If
    End If
End Function

'-----------------------------------------
' Distance and Geometry Related Functions
'-----------------------------------------

Private Function ComputeMinimumDistance(pt As Point3d, elements As Collection, bboxVerts() As Point3d) As Double
    Dim distBBox As Double
    distBBox = DistanceToPolygon(pt, bboxVerts)
    
    Dim distElem As Double
    distElem = distBBox ' Start with bounding box distance as baseline
    Dim elem As Element
    For Each elem In elements
        Dim dist As Double
        ' Ignore a few element types. Dimension element isn't intersectable and can have long ranges, rasters can have large ranges and be included somehow
        If elem.IsGraphical And Not elem.IsDimensionElement And Max(elem.Range.high.x - elem.Range.low.x, elem.Range.high.y - elem.Range.low.y) < 10000 Then
            dist = DistanceToElement(pt, elem)
            If dist < distElem Then
                distElem = dist
                If distElem < EPS Then Exit For
            End If
        End If
    Next elem
    If Not elem Is Nothing And False Then
        ' Debugging stuff
        If pt.x > 2562101 And pt.x < 2562255 And pt.y > 729519 And pt.y < 729628 Then
        Debug.Print distElem
        Debug.Print elem.Level.name
        Debug.Print elem.Type
        ActiveModelReference.UnselectAllElements
        ActiveModelReference.SelectElement elem
        End If
    End If
    ComputeMinimumDistance = distElem
End Function

Private Function DistanceToPolygon(pt As Point3d, polyVerts() As Point3d) As Double
    ' Polygon is the bounding box edges.
    ' Extract edges and find shortest distance
    Dim edges() As LineElement
    edges = PolygonToEdges(polyVerts)
    
    Dim minDist As Double
    minDist = 1E+30
    
    Dim i As Long
    For i = LBound(edges) To UBound(edges)
        Dim projPt As Point3d
        projPt = edges(i).ProjectPointOnPerpendicular2(pt, Matrix3dIdentity)
        Dim dist As Double
        dist = DistanceBetweenPoints(pt, projPt)
        If dist < minDist Then minDist = dist
    Next i
    
    DistanceToPolygon = minDist
End Function

Private Function PolygonToEdges(polyVerts() As Point3d) As LineElement()
    Dim cnt As Long
    cnt = UBound(polyVerts)
    Dim edges() As LineElement
    ReDim edges(0 To cnt)
    
    Dim i As Long
    For i = 0 To cnt - 1
        Set edges(i) = CreateLineElement2(Nothing, polyVerts(i), polyVerts(i + 1))
    Next i
    Set edges(cnt) = CreateLineElement2(Nothing, polyVerts(cnt), polyVerts(0))
    PolygonToEdges = edges
End Function

Private Function DistanceToElement(pt As Point3d, elem As Element) As Double
    If IsIntersectable(elem) Then
        ' Try projection
        Dim projPt As Point3d
        projPt = elem.AsIntersectableElement.ProjectPointOnPerpendicular2(pt, Matrix3dIdentity)
        DistanceToElement = DistanceBetweenPoints(pt, projPt)
    Else
        ' Non-intersectable: fallback to range
        DistanceToElement = DistanceToRange(pt, elem.Range)
    End If
End Function

Private Function DistanceToRange(pt As Point3d, rng As Range3d) As Double
    Dim dx As Double, dy As Double
    dx = 0#: dy = 0#
    
    If pt.x < rng.low.x Then
        dx = rng.low.x - pt.x
    ElseIf pt.x > rng.high.x Then
        dx = pt.x - rng.high.x
    End If
    
    If pt.y < rng.low.y Then
        dy = rng.low.y - pt.y
    ElseIf pt.y > rng.high.y Then
        dy = pt.y - rng.high.y
    End If
    
    DistanceToRange = Sqr(dx * dx + dy * dy)
End Function

Private Function DistanceToClosestVertex(pt As Point3d, verts() As Point3d) As Double
    Dim minDist As Double
    minDist = 1E+30
    Dim i As Long
    For i = LBound(verts) To UBound(verts)
        Dim d As Double
        d = DistanceBetweenPoints(pt, verts(i))
        If d < minDist Then minDist = d
    Next i
    DistanceToClosestVertex = minDist
End Function

Private Function DistanceBetweenPoints(a As Point3d, b As Point3d) As Double
    DistanceBetweenPoints = Point3dDistance(a, b)
End Function

Private Function IsIntersectable(elem As Element) As Boolean
    IsIntersectable = elem.IsIntersectableElement
    'Select Case elem.Type
    '    Case msdElementTypeLine, msdElementTypeLineString, msdElementTypeArc, msdElementTypeCurve
    '        IsIntersectable = True
    '    Case Else
    '        IsIntersectable = False
    'End Select
End Function

Private Function CanGetVertices(elem As Element, ByRef verts() As Point3d) As Boolean
    Select Case elem.Type
        Case msdElementTypeLine, msdElementTypeLineString, msdElementTypeShape
            verts = elem.AsLineElement.GetVertices()
            CanGetVertices = True
        Case Else
            CanGetVertices = False
    End Select
End Function

'-----------------------------------------
' Candidate Point Generation & Filtering
'-----------------------------------------

Private Function GenerateCandidatePoints(bboxVerts() As Point3d, d As Double) As clsCandidatePoint()
    Dim rng As Range3d
    rng = PolygonRange(bboxVerts)
    
    Dim GRID_SIZE As Long
    GRID_SIZE = 50
    
    Dim width As Double
    width = rng.high.x - rng.low.x
    Dim height As Double
    height = rng.high.y - rng.low.y
    
    Dim stepX As Double, stepY As Double
    stepX = width / GRID_SIZE
    stepY = height / GRID_SIZE
    
    Dim tempPoints() As clsCandidatePoint
    ReDim tempPoints(0 To GRID_SIZE * GRID_SIZE - 1)
    Dim idx As Long
    idx = 0
    
    Dim i As Long, j As Long
    For i = 0 To GRID_SIZE - 1
        For j = 0 To GRID_SIZE - 1
            Dim x As Double, y As Double
            x = rng.low.x + (i + 0.5) * stepX
            y = rng.low.y + (j + 0.5) * stepY
            
            Dim p As Point3d
            p = Point3dFromXY(x, y)
            
            If Point3dInPolygonXY(p, bboxVerts) <> -1 Then
                Set tempPoints(idx) = New clsCandidatePoint
                tempPoints(idx).pt = p
                idx = idx + 1
            End If
        Next j
    Next i
    
    If idx < UBound(tempPoints) Then
        ReDim Preserve tempPoints(0 To idx - 1)
    End If
    
    GenerateCandidatePoints = tempPoints
End Function

Private Function PolygonRange(polyVerts() As Point3d) As Range3d
    Dim minX As Double, minY As Double
    Dim maxX As Double, maxY As Double
    minX = polyVerts(0).x: maxX = minX
    minY = polyVerts(0).y: maxY = minY
    
    Dim i As Long
    For i = 1 To UBound(polyVerts)
        If polyVerts(i).x < minX Then minX = polyVerts(i).x
        If polyVerts(i).x > maxX Then maxX = polyVerts(i).x
        If polyVerts(i).y < minY Then minY = polyVerts(i).y
        If polyVerts(i).y > maxY Then maxY = polyVerts(i).y
    Next i
    
    Dim r As Range3d
    r.low = Point3dFromXYZ(minX, minY, 0)
    r.high = Point3dFromXYZ(maxX, maxY, 0)
    PolygonRange = r
End Function

Private Function FilterByDistance(points() As clsCandidatePoint, d As Double) As Collection
    Dim result As New Collection
    Dim i As Long
    For i = LBound(points) To UBound(points)
        If points(i).clearance >= d - EPS Then
            result.Add points(i)
        End If
    Next i
    Set FilterByDistance = result
End Function

'-----------------------------------------
' Region Identification
'-----------------------------------------

Private Function IdentifyRegions(points As Collection, d As Double) As Collection
    ' points is a collection of clsCandidatePoint objects
    ' We'll do a simple adjacency-based clustering

    Dim regions As New Collection
    If points.count = 0 Then
        Set IdentifyRegions = regions
        Exit Function
    End If
    Dim used() As Boolean
    ReDim used(1 To points.count)
    
    Dim i As Long, j As Long
    For i = 1 To points.count
        If Not used(i) Then
            Dim currentRegion As New Collection
            currentRegion.Add i
            used(i) = True
            
            Dim stack As New Collection
            stack.Add i
            
            Do While stack.count > 0
                Dim idx As Long
                idx = stack(stack.count)
                stack.Remove stack.count
                
                ' Check neighbors
                For j = 1 To points.count
                    If Not used(j) Then
                        Dim dist As Double
                        Dim cpt As clsCandidatePoint
                        Set cpt = points(idx)
                        Dim cpt1 As clsCandidatePoint
                        Set cpt1 = points(j)
                        dist = DistanceBetweenPoints(cpt.pt, cpt1.pt)
                        If dist < d * 2 Then
                            used(j) = True
                            currentRegion.Add j
                            stack.Add j
                        End If
                    End If
                Next j
            Loop
            
            ' Convert indices to a collection of clsCandidatePoint
            Dim regionCollection As New Collection
            Dim k As Long
            For k = 1 To currentRegion.count
                regionCollection.Add points(currentRegion(k))
            Next k
            
            regions.Add regionCollection
        End If
    Next i
    
    Set IdentifyRegions = regions
End Function

'-----------------------------------------
' Placing Points in a Region
'-----------------------------------------

Private Function PlacePointsInRegion(pointCollection As Collection, d As Double) As Collection
    Dim result As New Collection
    Dim used() As Boolean
    ReDim used(1 To pointCollection.count)
    
    Dim i As Long, j As Long
    For i = 1 To pointCollection.count
        If Not used(i) Then
            result.Add pointCollection(i)
            For j = 1 To pointCollection.count
                If Not used(j) Then
                    Dim dist As Double
                    Dim cpt As clsCandidatePoint
                    Set cpt = pointCollection(i)
                    Dim cpt1 As clsCandidatePoint
                    Set cpt1 = pointCollection(j)
                    dist = DistanceBetweenPoints(cpt.pt, cpt1.pt)
                    If dist < d - EPS Then
                        used(j) = True
                    End If
                End If
            Next j
        End If
    Next i
    
    Set PlacePointsInRegion = result
End Function

'-----------------------------------------
' Utilities
'-----------------------------------------

Private Sub SortByClearance(ByRef pointCollection As Collection)
    Dim i As Long, j As Long
    Dim temp As clsCandidatePoint
    
    ' Bubble sort:
    ' If pointCollection(j).clearance > pointCollection(i).clearance,
    ' move pointCollection(j) before i to achieve descending order.
    For i = 1 To pointCollection.count - 1
        For j = i + 1 To pointCollection.count
            If pointCollection(j).score > pointCollection(i).score Then
                ' Store the item
                Set temp = pointCollection(j)
                ' Remove the item from its current position
                pointCollection.Remove j
                ' Insert it before position i
                pointCollection.Add temp, , i
            End If
        Next j
    Next i
End Sub
